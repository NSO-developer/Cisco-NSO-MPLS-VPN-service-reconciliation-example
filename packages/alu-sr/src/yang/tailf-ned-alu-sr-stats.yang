module tailf-ned-alu-sr-stats {
  namespace 'http://tail-f.com/ned/alu-sr/stats';
  prefix alu-stats;

  import tailf-common {
    prefix tailf;
  }

  import tailf-ncs {
    prefix ncs;
  }

  /// ========================================================================
  /// exec
  /// ========================================================================

  container exec {
    tailf:info "Execute commands on device";

    // admin [arg 1] .. [arg N]
    tailf:action admin {
      tailf:info "Execute admin commands";
      tailf:actionpoint ncsinternal {
        tailf:internal;
      }
      input {
        leaf-list args {
          tailf:cli-drop-node-name;
          tailf:cli-flat-list-syntax;
          type string {
            tailf:info "admin argument(s)";
          }
        }
      }
      output {
        leaf result {
          type string;
        }
      }
    }

    // show [arg 1] .. [arg N]
    tailf:action show {
      tailf:info "Execute show commands";
      tailf:actionpoint ncsinternal {
        tailf:internal;
      }
      input {
        leaf-list args {
          tailf:cli-drop-node-name;
          tailf:cli-flat-list-syntax;
          type string {
            tailf:info "show argument(s)";
          }
        }
      }
      output {
        leaf result {
          type string;
        }
      }
    }


    // debug [arg 1] .. [arg N]
    tailf:action debug {
      tailf:info "Execute debug commands";
      tailf:actionpoint ncsinternal {
        tailf:internal;
      }
      input {
        leaf-list args {
          tailf:cli-drop-node-name;
          tailf:cli-flat-list-syntax;
          type string {
            tailf:info "debug argument(s)";
          }
        }
      }
      output {
        leaf result {
          type string;
        }
      }
    }


    // ping [arg 1] .. [arg N]
    tailf:action ping {
      tailf:info "Send echo messages";
      tailf:actionpoint ncsinternal {
        tailf:internal;
      }
      input {
        leaf-list args {
          tailf:cli-drop-node-name;
          tailf:cli-flat-list-syntax;
          type string {
            tailf:info "ping argument(s)";
          }
        }
      }
      output {
        leaf result {
          type string;
        }
      }
    }
  }
}
