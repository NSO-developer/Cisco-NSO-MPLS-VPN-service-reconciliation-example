// =========================================================================
//                          alu NED
// =========================================================================

module tailf-ned-alu-sr {
  namespace 'http://tail-f.com/ned/alu-sr';
  prefix alu;

  import tailf-common {
    prefix tailf;
  }

  import ietf-inet-types {
    prefix inet;
  }

  // =========================================================================
  // REVISION
  // =========================================================================
 revision 2015-06-11 {
    description
    "3.4
     New release.
     Enhancements:
     Corrections:
      Use explicit-exit annotation in / router * / policy-options
      Major YANG model change. Most shutdown leafs now modelled as booleans
      with default values.
    ";
 }

 revision 2015-06-01 {
    description
    "3.2.6.1
     Enhancements:
     Corrections:
      Make the NED calculate transid evel when it is connected to a netsim
      device.
    ";
 }

 revision 2015-05-29 {
    description
    "3.2.6
     New release.
     Enhancements:
     Corrections:
      Fixed a dependency issue in / port *
    ";
 }

 revision 2015-05-28 {
    description
    "3.2.4.12
    Enhancements:
       Added set hooks at the locations below to mimic the behavior of the
       device;
        / router * / mpls
        / qos / network-queue *
       Additions to the YANG model in
       / router * / bgp / group * / neighbor * /
       / router * / bgp / group * /
       / router * / ldp
       / router *
    Corrections:
       / router * / rsvp repends on / router * / mpls
       Fixed misspelled leaf 'local-preferences' to 'local-preference'
       Use flat-list-syntax on all leaf-lists
       Fixed dependency issue with
       / router * / interface * / port

    ";
  }

 revision 2015-05-25 {
    description
    "3.2.4.11
    Enhancements:
     Added // qos / sap-ingress * / queue * / adaption-rule
    Corrections:
     Added tailf:dependency to // cflowd / cache-size / collector * /
      template-set
    ";
  }

  revision 2015-05-25 {
    description
    "3.2.4.10
    Enhancements:
     Added
      / system / security / tacplus *
      / router * / bgp / group * / neighbor * / peer-as
    Corrections:
     Fixed YANG model bugs in
     / router * / policy-options / begin / policy-statement * / default-action
     / system / security / source-address
     / system / security / snmp
    ";
  }

  revision 2015-05-21 {
    description
    "3.2.4.9
    Enhancements:
      The NED is now automatically storing information about OS version
      and machine model in / devices / device * / platform
      Added:
        // qos / fabric-profile
        // card * / mda * / access / ingress / fabric-policy
        // card * / mda * / network / ingress / fabric-policy
        // ip-address-range
        // card * / mda * / network / ingress / pool
        // cflowd /
        // ipsec /
        // isa /
        // port * / ethernet / ingress-rate
        // port * / modify-buffer-allocation-rate /
        // port * / network /
        // port * / tdm / ds1 * / clock-source
        // port * / tdm / ds3 * / clock-source
        // qos / sap-ingress * / prec
        // qos / sap-ingress * / queue * / adaption-rule
        // qos / sap-ingress * / default-priority
        // qos / sap-ingress * / queue * / adaption-rule
        // qos / slope-policy * / description
        // log / accounting-policy * /
        // service / ies * / interface * / tos-marking-state
        // service / vpls * / sap * / restrict-protected-src
        // service / vpls * / bgp-vpls
        // service / vprn * / dhcp
        // service / vprn * / dhcp / local-dhcp-server *
        // service / vprn * / ipsec
        // service / vprn * / bgp / damping
        // service / vprn * / interface * / sap * / collect-stats
        // service / vprn * / interface * / sap * / ipsec-tunnel
        // service / vprn * / spoke-sdp *
        // service / vprn * / static-route * ipsec-tunnel
        // service / vprn * / pim / rp / static / address *
        // service / vprn * / mvpn / provider-tunnel / inclusive / pim
        // service / pw-template * / use-provisioned-sdp
        // router * / ospf3
        // router * / mpls / resignal-timer
        // router * / mpls / srlg-frr
        // router * / policy-options
        // router * / pim / rp / static / address *
        // router * / pim / rp / bsr-candidate
        // router * / pim / rp / rp-candidate
        // test-oam /
        // mirror / mirror-dest * type
        // saa /

    Corrections:
      In / service / pw-template *
      Use flat-list-syntax in
      / router * / bgp / group * / family
    ";
  }

  revision 2015-05-11 {
    description
    "3.2.4.8
    Enhancements:
      Additions to
       / router * / pim /
       / router * / pim / interface *
       / filter / ipv6-filter * / entry * / match / next-header
       / service / ies * / interface * / sap * / egress / filter
       / service / ies * / interface * / sap * / ingress / filter
    Corrections:
    ";
  }

  revision 2015-05-04 {
    description
    "3.2.4.7
    Enhancements:
      Additions to
       / service / vprn * / dhcp
       / service / vprn * / ipsec
    Corrections:
      Added dependency on
       / service vpls * / sap * / multi-service-site
    ";
  }

  revision 2015-04-23 {
    description
    "3.2.4.6
    Enhancements:
      Added new config under
       / service / vprn * / ipsec
       / service / vprn * / dhcp
    Corrections:
      Changed model for most of the shutdown leaf. Now modelled as boolean
      with a default value. Previously modelled as empty with a cli-show-no
      annotation.
    ";
  }

  revision 2015-04-09 {
    description
    "3.2.4.5
    Enhancements:
    Corrections:
      Added more SAP dependencies. A SAP entry is unique througout the
      system. I.e a SAP id can only exist once in either the vpls, ies,
      vprn or epipe lists.
    ";
  }

  revision 2015-04-08 {
    description
    "3.2.4.4
    Enhancements:
      Added / service / vpls * / interface *
    Corrections:
    ";
  }

  revision 2015-04-02 {
    description
    "3.2.4.3
    Enhancements:
    Corrections:
       Solved dependency issue between:
         / router * / ospf * / area * / interface
       and
         / router * / interface
       Added dependency between:
         / router * / interface
       and
         / port * /
       Added non-strict-leafref on:
         / router * / interface * / qos
    ";
  }

  revision 2015-03-19 {
    description
    "3.2.4.2
    Enhancements:
    Corrections:
       Changed the following leafs to enumerations:
       / port * / ethernet / mode
       / port * / ethenet / encap-type
       Added dependency between:
       / port * / ethernet / network and / port * / ethernet / mode
       The following leaf is now a non-strict leafref:
       / port * / ethernet / network / queue-policy
     ";
   }

  revision 2015-03-11 {
    description
    "3.2.2.3
     Verified with NCS-3.4
    Enhancements:
    Corrections:
     Changed order of
     / port * / ethernet / mode and / port * / ethernet / encap-type
     ";
   }

   revision 2015-03-05 {
    description
    "3.2.2.2
    Enhancements:
     New elements added under
     / port * / ethernet
     / qos / port-scheduler-policy
     / qos / policer-control-policy
     / router * / mpls / static-lsp
    Corrections:
     Changed to a non strict leafreaf at the following location
     / service / sdp * / lsp
    ";
   }

   revision 2015-03-03 {
    description
    "3.2.2.1
    Enhancements:
     New elements added under / router * / ospf *
    Corrections:
     Changed the key for the / router * / ospf * list to be compliant with
     the device. An ospf instance id is used instead of previously the ospf
     router id.
    ";
    }

   revision 2015-02-20 {
    description
    "3.2.2
    Enhancements:
    Corrections:
     Minor fixes done at the following after testing with a real device:
      / sap  * / egress / scheduler-policy
      / port * / shutdown
      / service / customer * / multi-service-site
      / service / ies * / interface * / ipv6 dhcp6-relay / shutdown
      / service / vpls * / sap * / egress
      / service / vpls * / bgp-ad
      / system /  time / sntp / shutdown
      / router * / interface * / port
    ";
   }

   revision 2015-02-18 {
    description
    "3.2.1.9
    Enhancements:
      Addition in
      // service / vprn * / interface * / ipv6
      // service / vprn * / router-id
      // service / vprn * / isis *
      // router * / pim /
      // system / security / profile / entry *
    Corrections:
    ";
  }

  revision 2015-02-17 {
    description
    "3.2.1.8
    Enhancements:
      Addition in
      / service / vpls * / pim-snooping
      / service / vpls * / spoke-sdp * split-horizon-group
      / service / vprn * / bgp / authentication-key
      / service / vprn * / bgp / group * /
      / service / vprn * / interface * /
    Corrections:
    ";
  }

  revision 2015-02-12 {
    description
    "3.2.1.7
    Enhancements:
     Additions in
      / sap  * / egress / qinq-mark-top-only
      / card  * / network
      / port * / ethernet / lldp
      / port / ethernet / network
      / qos / network-queue * / queue * / port-parent
      / qos / sap-egress * / fc * / burst-limit
      / qos / slope-policy *
      / qos / port-scheduler-policy *
      / eth-cfm / domain * / name
      / log / file-id * / description
      / log / log-id * / to
      / log / syslog * / level
      / service / vpls * / allow-ip-int-binding
      / service / vpls * / service-name
      / service / vpls * / bgp
      / service / vpls * / bgp-ad
      / service / vprn * / interface * / secondary
      / service / vprn * / interface * / vpls *
      / service / vprn * / static-route *
      / service / vprn * / sgt-qos
      / service / vprn * / pim
      / service / vprn * / mvpn
      / service / pw-template *
      / router * / ospf / area * / interface
      / router * / ospf
      / router * / mpls / lsp-template *
      / router * / ldp / interface-parameters
      / router * / rsvp /   authentication-key
      / router * / interface * / bfd
      / router * / policy-options / as-path
      / router * / pim
      / system / chassis-mode * / power-supply *
      / system / security
      / filter / mac-filter * / entry *
    ";
  }

  revision 2015-02-10 {
    description
      "3.2.1.6
      Enhancements:
        Extended the proxy server connection setup with support for serial
        terminal servers.

        Added support for running some native commands as actions through the
        device live-status in the NCS CLI.
      Corrections:
        Added diff-dependency between / router * / router-advertisement
        and / service / ies *
        Added diff-dependency between / router * / mld and / service / ies *
      ";
  }

  revision 2015-01-13 {
    description
      "3.2.1.4
       Enhancements:

       Corrections:
        Using real leafref instead of non-strict-leafref on:
         / service / vpls * / sap  * / multi-service-site
         / service / epipe * / sap  * / multi-service-site
         / service / ies * / sap  * / multi-service-site
      ";
  }

  revision 2015-01-12 {
    description
      "3.2.1.3
       Enhancements:

       Corrections:
        Added appropriate leafref dependencies
          towards:
          / service / customer * / multi-service-site
          for:
          / service / vpls * / sap  * / multi-service-site
          / service / epipe * / sap  * / multi-service-site
          / service / ies * / sap  * / multi-service-site
        Added appropriate trigger-on-set dependencies between:
          / service / vpls * / sap * / multi-service-site
          and
          / service / vpls * / sap * / egress / schedule-policy
        ";
  }

  revision 2014-12-19 {
    description
      "3.2.1.2
       Enhancements:

       Corrections:
       Changed the order of scheduler-policy and scheduler-override at the
       following locations:
        / service / customer * / multi-service-site * / ingress
        / service / customer * / multi-service-site * / egress
       Removed create leaf from:
        / router * / mld / interface *
      ";
  }

  revision 2014-12-02 {
    description
      "3.2.1.1
       Enhancements:

       Corrections:
       added missing cli-no-value-on-delete on the following leaf:
        / service / customer * / multi-service-site * / egress / scheduler-polic
      ";
  }

  revision 2014-11-26 {
    description
      "3.2.1
      New release
      ";
  }

  revision 2014-11-24 {
    description
      "3.2.0.2
      Enhancements:
      NED config parameters in tailf-alu-sr-meta.yang are now configurable
      on global, profile and device level,

      Corrections:
      ";
  }

  revision 2014-11-20 {
    description
      "3.2.0.1
       Enhancements:
       More info strings
       Additions in / port / ethernet / hold-time
       Additions in / port * / dwdm /
       Additions in / port * / otu
       Additions in / router *
       Additions in / router * / isis * / level
       Additions in / system / rollback
       Additions in / system / time / ntp

       Corrections:
       Added missing cli-add-mode in / port * / dwdm / coherent
       Added missing cli-add-mode in / system / ethernet
       Added support for ipv6 in / service / vprn * / bgp / group * / neighbor
       Fixed annotation issue with / service / customer * / multi-service-site
        * / ingress / rate
       Fixed annotation issue with / service / customer * / multi-service-site
        * / egress / rate
       ";
  }

  revision 2014-11-18 {
    description
      "3.2
       Prepared for release";
  }

  revision 2014-11-10 {
    description
      "3.1.0.7
      Added tailf:cli-explicit-exit to router * / policy-options
      Changed / router * / isis. Is now a list.
      Added new functionality in / router / isis * /
      Added new functionality in / service / ies * / ipv6 / dhcp6-relay
      Added new functionality in / service / ies * / interface *
      Added basic support for / log
      Added support for / router * / bgp
      Added support for / router * / router-advertisement
      Added missing annotation in / router * / interface * / port.
      Added missing annotation in lag * / lacp.
      Changed filter / ip-filter * / embed-filter to a non-strict-leafref";
  }

  revision 2014-11-07 {
    description
      "3.1.0.6
       added missing cli-no-value-on-delete on the following leaf:
       service / customer * / multi-service-site * / ingress / scheduler-polic";
  }

  revision 2014-11-03 {
    description
      "3.1.0.5
     Added support for configurable behaviour upon admin-save failure.
     This feauture is modelled in the tailf-alu-sr-meta.yang";
  }


  revision 2014-10-31 {
    description
      "3.1.0.4
      Added support for / qos / queue-group-templates
      Added support for / service / vpls * / mesh-sdp * / ingress / qos";
  }

  revision 2014-10-09 {
    description
      "3.1.0.2
       Leaf /service / vpls * / mesh-sdb * / def-mesh-vc-id must have its
       value present when deleted and can only be deleted after mesh-sdp";
  }

  revision 2014-10-03 {
    description
      "3.1.0.1
        Fixed a sequence issue in filter / ip-filter * / match / dst-port
        Fixed a sequence issue with filter / ip-filter * / match / src-port";
  }

  revision 2014-09-11 {
    description
      "3.1
      Added missing annotation in / router * / interface * / port.
      Added missing annotation in lag * / lacp.
        Changed filter / ip-filter * / embed-filter to a non-strict-leafref";
  }

  revision 2014-09-05 {
    description
      "3.0.2.0
      Using new tail:cli-diff-dependency extension to solve creation order
      of SAP objects in different subtrees.";
  }

  revision 2014-08-20 {
    description
      "3.0.1.1
      Added support for router * / policy-options
      Added more complete support for service / vprn *";
  }

  revision 2014-08-13 {
    description
      "Various minor fixes to the system / security / cpm-filter subtree";
  }

  revision 2014-08-11 {
    description
      "Various minor fixes in system, redundancy and filter subtrees";
  }

  revision 2014-07-03 {
    description
      "Changed modelling of the shutdown leafs. They are now modelled as type
       empty and with tailf:cli-show-no extension. Done to get rid of
       out-of-sync issues caused by the ALU device when it automatically
       displays shutdown/no shutdown even when it has not explicitly been set
     ";
  }

  revision 2014-06-11 {
    description
      "Added support for new config specific for ALU 7210 devices";
  }

  revision 2014-06-08 {
    description
      " Added support for
        - vpls * / sap * / auto-learn-mac-protect
        - vpls * / sap * / restrict-protected-src
        - vpls * / mesh-sdp * / auto-learn-mac-protect
        - vpls * / mesh-sdp * / restrict-protected-src";
  }

  revision 2014-06-05 {
    description
      "- Replaced all ipv6-with-prefix with ipv6-address-and-prefix-length
       - All description leaf now tagged with tailf:cli-no-value-on-delete";
  }

  revision 2014-05-23 {
    description
      "- Added support for debug/mirror-source configurations
      - Added support for mirror/mirror-destination configurations
      - Disabled the scope-leaf under filter/ip-filter and filter/ipv6-filter
        The reason is that this leaf is not displayed properly when the ALU
        device dumps the configurations. This results in out-of-sync issues
      - Moved ip-filter-entry to a grouping used by all nodes implementing
        filter entries.
      - Added support for service/ies/interface/sap/ingress/queue-override
      - Added support for service/ies/interface/sap/egress/queue-override
      - Fixed minor issues in qos/scheduler-policy
      - Added qos/sap-egress/ip-criteria
      - Added qos/sap-egress/ipv6-criteria
      - Changed type ipv4-prefix to tailf:ipv4-address-and-prefix-length
      - Changed type ipv6-prefix to tailf:ipv6-address-and-prefix-length
      - Fixed bug in service/ies/interface/ipv6/dhcp6-relay/shutdown
      - Fixed leafref in router * / . All subtrees with interface leaf shall
        refer to router/interface.
      - Implemented router/ldp/targeted-session/peer";
  }

  revision 2014-04-28 {
    description
      "- Added support for service/vpls configurations
       - Fixed issues related to acl on filter/ip-filter
         and filter/ipv6-filter.
       - SAP id is now a plain string in order to support all the
         ~20 different id formats.
       - Added comments to make the yang code easier to navigate.
       - Added limited support for service/vprn configurations.
       - Added limited support for router/ospf configurations.
       - Added limited support for router/mpls configurations.
       - Added limited support for router/l2tp configurations.
       - Added limited support for router/ldp configurations.
       - Added an action <native-cmd> that allows sending strings
         containing native commands directly to the target.";
  }

  revision 2014-01-31 {
    description
      "Added support for filter ip-filter";
  }

  // =========================================================================
  // TYPEDEF
  // =========================================================================


  // DSCP type
  typedef dscp-type {
    type enumeration {
      enum be;
      enum ef;
      enum cp1;
      enum cp2;
      enum cp3;
      enum cp4;
      enum cp5;
      enum cp6;
      enum cp7;
      enum cp9;
      enum cs1;
      enum cs2;
      enum cs3;
      enum cs4;
      enum cs5;
      enum nc1;
      enum nc2;
      enum af11;
      enum af12;
      enum af13;
      enum af21;
      enum af22;
      enum af23;
      enum af31;
      enum af32;
      enum af33;
      enum af41;
      enum af42;
      enum af43;
      enum cp11;
      enum cp13;
      enum cp15;
      enum cp17;
      enum cp19;
      enum cp21;
      enum cp23;
      enum cp25;
      enum cp27;
      enum cp29;
      enum cp31;
      enum cp33;
      enum cp35;
      enum cp37;
      enum cp39;
      enum cp41;
      enum cp42;
      enum cp43;
      enum cp44;
      enum cp45;
      enum cp47;
      enum cp49;
      enum cp50;
      enum cp51;
      enum cp52;
      enum cp53;
      enum cp54;
      enum cp55;
      enum cp57;
      enum cp58;
      enum cp59;
      enum cp60;
      enum cp61;
      enum cp62;
      enum cp63;
    }
  }

  // VPLS id type
  typedef vpls-id {
    type union {
      type string {
        length "1..64";
        tailf:info "<string id>;; max length 64";
      }
      type uint32 {
        range "1..2147483647";
        tailf:info "<numeric id>;;[1..2147483647]";
      }
    }
  }

  // IEEE mac address
  typedef ieee-mac {
    tailf:info "<ieee mac address>;; xx:xx:xx:xx:xx:xx or xx-xx-xx-xx-xx-xx";
    type string;
  }

  // Direction type
  typedef direction {
    tailf:info "<direction>;; up | down";
    type enumeration {
      enum up;
      enum down;
    }
  }

  // Test pattern used in eth-test configurations
  typedef test-pattern {
    type enumeration {
      enum all-zeros;
      enum all-ones;
    }
  }

  // Mac move limits type
  typedef limit-mac-move {
    type enumeration {
      enum blockable;
      enum non-blockable;
    }
  }

  // Filter action
  typedef filter-action {
    type enumeration {
      enum permit;
      enum deny;
      enum deny-host-unreachable;
    }
  }

  typedef adaption-rule {
    type enumeration {
      enum max;
      enum min;
      enum closest;
    }
  }

  // protocol
  typedef protocol {
    type union {
      type enumeration {
        enum none;
        enum crtp;
        enum crudp;
        enum egp;
        enum eigrp;
        enum encap;
        enum ether-ip;
        enum gre;
        enum icmp;
        enum idrp;
        enum igmp;
        enum igp;
        enum ip;
        enum ipv6;
        enum ipv6-frag;
        enum ipv6-icmp;
        enum ipv6-no-nxt;
        enum ipv6-opts;
        enum ipv6-route;
        enum isis;
        enum iso-ip;
        enum l2tp;
        enum ospf-igp;
        enum pim;
        enum pnni;
        enum ptp;
        enum rdp;
        enum rsvp;
        enum stp;
        enum tcp;
        enum udp;
        enum vrrp;
        enum *;
      }
      type uint8 {
        range "1..255";
      }
      type string;
    }
  }

  // icmp-type
  typedef icmp-type {
    type union {
      type uint8;
      type enumeration {
        enum none;
        enum echo-reply;
        enum dest-unreachable;
        enum source-quench;
        enum redirect;
        enum echo-request;
        enum router-advt;
        enum router-selection;
        enum time-exceeded;
        enum parameter-problem;
        enum timestamp-request;
        enum timestamp-reply;
        enum addr-mask-request;
        enum addr-mask-reply;
      }
    }
  }

  // icmpv6-type
  typedef icmpv6-type {
    type union {
      type uint8;
      type enumeration {
        enum "redirect";
        enum "packet-too-big";
        enum "redirect-message";
        enum "echo-reply";
        enum "echo-request";
        enum "time-exceeded";
        enum "dest-unreachable";
        enum "router-advt";
        enum "router-solicitation";
        enum "neighbor-solicitation";
        enum "neighbor-advertisement";
        enum "multicast-listen-report";
        enum "multicast-listen-done";
      }
    }
  }

  // =========================================================================
  // GROUPING
  // =========================================================================

  // src-dst-ip
  grouping src-dst-ip {
    leaf src-ip {
      type union {
        type inet:ipv4-prefix;
        type string;
      }
    }
    leaf dst-ip {
      type union {
        type inet:ipv4-prefix;
        type string;
      }
    }
  }

  // ip-address-range
  grouping ip-address-range {
    list low-high-list {
      tailf:cli-drop-node-name;
      tailf:cli-suppress-mode;
      tailf:cli-delete-when-empty;
      key "low high";
      leaf low {
        type inet:ipv4-address {
          tailf:info "<start-ip-address>";
        }
      }
      leaf high {
        type inet:ipv4-address {
          tailf:info "<stop-ip-address>";
        }
      }
    }
  }

  // eth-cfm
  grouping eth-cfm {

    // eth-cfm / mep *
    list  mep {
      tailf:info "Configure a CFM Virtual Maintenance Endpoint";
      tailf:cli-embed-no-on-delete;
      tailf:cli-sequence-commands;
      key "mep-id";

      leaf mep-id {
        tailf:info "mep-id;;<1..8191>";
        mandatory true;
        type uint16 {
          range "1..8191";
        }
      }

      leaf domain {
        tailf:cli-hide-in-submode;
        tailf:info "md-index;;<1..4294967295>";
        type leafref {
          path "/alu:eth-cfm/domain/id";
        }
        mandatory true;
        // type uint32 {
        //   range "1..4294967295";
        // }
      }

      leaf association {
        tailf:cli-hide-in-submode;
        tailf:info "ma-index;;<1..4294967295>";
        type leafref {
          path "/alu:eth-cfm/domain/association/ma-index";
        }
        mandatory true;
        // type uint32 {
        //   range "1..4294967295";
        // }
      }

      // eth-cfm / mep * direction
      leaf direction {
        tailf:info "<up | down>";
        tailf:cli-hide-in-submode;
        tailf:cli-no-name-on-delete;
        tailf:cli-no-value-on-delete;
        type direction;
      }

      // eth-cfm / mep * / ais-enable /
      container ais-enable {
        tailf:cli-add-mode;
        tailf:cli-embed-no-on-delete;
        tailf:cli-break-sequence-commands;

        // eth-cfm / mep * / ais-enable / client-meg-level
        leaf-list client-meg-level {
          tailf:cli-flat-list-syntax;
          tailf:cli-no-value-on-delete;
          type uint8 {
            range "1..7";
          }
        }

        // eth-cfm / mep * / ais-enable / description
        leaf description {
          tailf:cli-embed-no-on-delete;
          type string;
        }

        // eth-cfm / mep * / ais-enable / interval
        leaf interval {
          tailf:cli-embed-no-on-delete;
          type enumeration {
            enum 1;
            enum 60;
          }
        }

        // eth-cfm / mep * / ais-enable / priority
        leaf priority {
          tailf:cli-embed-no-on-delete;
          type uint8 {
            range "0..7";
          }
        }
      }

      // eth-cfm / mep * / ccm-enable
      leaf ccm-enable {
        tailf:info "Enable/Disable Generation of CCM messages";
        tailf:cli-embed-no-on-delete;
        type empty;
      }

      // eth-cfm / mep * / ccm-ltm-priority
      leaf ccm-ltm-priority {
        tailf:info "Configure the priority of CCM and LTM messages";
        tailf:cli-embed-no-on-delete;
        type uint8 {
          range "0..7";
        }
      }

      // eth-cfm / mep * / ccm-padding-size
      leaf ccm-padding-size {
        tailf:info "Insert additional padding in the CCM packets";
        tailf:cli-embed-no-on-delete;
        type uint32;
      }

      // eth-cfm / mep * / description
      leaf description {
        tailf:info "Add/remove a text description for the MEP";
        tailf:cli-embed-no-on-delete;
        type string;
      }

      // eth-cfm / mep * / eth-test-enable
      container eth-test-enable {
        tailf:info "Enable/Disable eth-test functionality on MEP";
        tailf:cli-add-mode;
        tailf:cli-embed-no-on-delete;
        uses eth-test;
      }

      // eth-cfm / mep * / fault-propagation-enable
      leaf fault-propagation-enable {
        tailf:info "Configure the Fault Propagation for the MEP";
        tailf:cli-embed-no-on-delete;
        type enumeration {
          enum use-if-tlv;
          enum suspend-ccm;
        }
      }

      // eth-cfm / mep * / low-priority-defect
      leaf low-priority-defect {
        tailf:info "Configure the Lowest Priority Defect for the MEP";
        type enumeration {
          enum allDef;
          enum macRemErrXcon;
          enum remErrXcon;
          enum errXcon;
          enum Xcon;
          enum noXcon;
        }
      }

      // eth-cfm / mep * / mac-address
      leaf mac-address {
        tailf:info "Configure the MAC Address for the MEP";
        tailf:cli-embed-no-on-delete;
        type ieee-mac;
      }

      // eth-cfm / mep * / one-way-delay-threshold
      leaf one-way-delay-threshold {
        tailf:info "Configure the one-way-delay test threshold";
        type uint16 {
          range "0..600";
        }
      }

      // eth-cfm / mep * / shutdown
      leaf shutdown {
        tailf:info "Administratively enable/disable the MEP";
        tailf:cli-boolean-no;
        default true;
        type boolean;
      }
    }
  }

  // igmp-snooping
  grouping igmp-snooping {

    // igmp-snooping disable-router-alert
    leaf disable-router-alert {
      tailf:cli-embed-no-on-delete;
      type empty;
    }

    // igmp-snooping fast-leave
    leaf fast-leave {
      tailf:cli-embed-no-on-delete;
      type empty;
    }

    // igmp-snooping import
    leaf import {
      tailf:cli-embed-no-on-delete;
      type string {
        length "1..32";
      }
    }

    // igmp-snooping last-member-query-interval
    leaf last-member-query-interval {
      tailf:cli-embed-no-on-delete;
      type uint8 {
        range "1..50";
      }
    }

    // igmp-snooping max-num-groups
    leaf max-num-groups {
      tailf:cli-embed-no-on-delete;
      type uint16 {
        range "1..1000";
      }
    }

    // igmp-snooping mrouter-port
    leaf mrouter-port {
      tailf:cli-embed-no-on-delete;
      type empty;
    }

    // igmp-snooping query-interval
    leaf query-interval {
      tailf:info "Configure the IGMP Query Interval for v1/v2 Queriers";
      tailf:cli-embed-no-on-delete;
      type uint16 {
        range "2..1024";
      }
    }

    // igmp-snooping query-response-interval
    leaf query-response-interval {
      tailf:cli-embed-no-on-delete;
      type uint16 {
        range "1..1023";
      }
    }

    // igmp-snooping robust-count
    leaf robust-count {
      tailf:cli-embed-no-on-delete;
      type uint8 {
        range "1..255";
      }
    }

    // igmp-snooping send-queries
    leaf send-queries {
      tailf:cli-embed-no-on-delete;
      type empty;
    }

    // igmp-snooping static
    container static {
      tailf:cli-add-mode;

      // igmp-snooping static / group *
      list group {
        tailf:cli-embed-no-on-delete;
        max-elements 1;
        key group-address;

        leaf group-address {
          tailf:cli-hide-in-submode;
          type inet:ip-address;
        }

        leaf stdarg {
          tailf:cli-embed-no-on-delete;
          type string;
        }
      }
    }

    // igmp-snooping version
    leaf version {
      tailf:cli-embed-no-on-delete;
      type uint8;
    }
  }

  // sdp-common
  grouping sdp-common {

    // sdp sdp-id
    leaf sdp-id {
      tailf:non-strict-leafref {
        path "/alu:service/sdp/sdp-id";
      }
      type uint32;
    }

    // sdp vc-id
    leaf vc-id {
      type uint32;
    }

    // sdp vc-type
    leaf vc-type {
      tailf:cli-hide-in-submode;
      tailf:cli-no-name-on-delete;
      tailf:cli-no-value-on-delete;
      type enumeration {
        enum ether;
        enum vlan;
      }
    }

    // sdp endpoint
    leaf endpoint {
      tailf:cli-hide-in-submode;
      tailf:cli-no-name-on-delete;
      tailf:cli-no-value-on-delete;
      tailf:non-strict-leafref {
        path "/alu:service/epipe/endpoint/endpoint-name";
      }
      type string;
    }

    // sdp shutdown
    leaf shutdown {
      tailf:cli-boolean-no;
      default false;
      type boolean;
    }

    // sdp create
    leaf create {
      tailf:cli-hide-in-submode;
      tailf:cli-no-name-on-delete;
      mandatory true;
      type empty;
    }
  }

  // sdp-spoke-mesh-common
  grouping sdp-spoke-mesh-common {
    uses sdp-common;

    // accounting-policy
    leaf accounting-policy {
      tailf:info "Configure accounting-policy to be used";
      tailf:cli-no-value-on-delete;
      type uint8 {
        range "1..99";
      }
    }

    // auto-learn-mac-protect
    leaf auto-learn-mac-protect {
      tailf:info "Enable/disable automatic update of MAC protect list";
      tailf:cli-embed-no-on-delete;
      type empty;
    }


    // collect-stats
    leaf collect-stats {
      tailf:info "Enable/disable statistics collection";
      tailf:cli-embed-no-on-delete;
      type empty;
    }

    //  egress
    container egress {
      tailf:info "SDP binding egress configuration";
      tailf:cli-add-mode;

      // egress / filter
      container filter {
        tailf:info "Apply egress filter";
        tailf:cli-embed-no-on-delete;
        uses filter-choice;
      }

      // egress / qos
      container qos {
        tailf:info "Configure egress qos";
        tailf:cli-embed-no-on-delete;
        tailf:cli-sequence-commands;
        tailf:cli-compact-syntax;

        // egress / qos / network-policy-id
        leaf network-policy-id {
          tailf:info "<network-policy-id>";
          tailf:cli-drop-node-name;
          tailf:cli-no-value-on-delete;
          type uint16;
          tailf:non-strict-leafref {
            path "/alu:qos/sap-egress/policy-id";
          }
        }

        // egress / qos port-redirect-group
        leaf port-redirect-group {
          tailf:info "<queue-group-name>";
          tailf:cli-no-name-on-delete;
          tailf:cli-no-value-on-delete;
          tailf:non-strict-leafref {
            path "/alu:qos/queue-group-templates/egress/"
              +"queue-group/queue-group-name";
          }
          type string;
        }

        // egress / qos instance
        leaf instance {
          tailf:info "<instance-id>";
          tailf:cli-no-name-on-delete;
          tailf:cli-no-value-on-delete;
          type uint16 {
            range "1..16384";
          }
        }
      }

      // egress / vc-label
      leaf vc-label {
        tailf:info "Configure egress label";
        type uint32 {
          range "16..1048575";
        }
      }
    }

    // eth-cfm
    container eth-cfm {
      tailf:info "Configure CFM parameters";
      tailf:cli-add-mode;
      uses eth-cfm;
    }

    // force-vlan-forwarding
    leaf force-vlan-forwarding {
      tailf:info "Forces vlan-vc-type forwarding in the data-path";
      type empty;
    }

    // igmp-snooping
    container igmp-snooping {
      tailf:info "Configure IGMP snooping parameters";
      uses igmp-snooping;
    }

    // ingress /
    container ingress {
      tailf:info "SDP binding ingress configuration";
      tailf:cli-add-mode;

      // ingress / filter
      container filter {
        tailf:info "Apply ingress filter";
        tailf:cli-embed-no-on-delete;
        uses filter-choice;
      }

      // ingress / qos
      container qos {
        tailf:info "Configure egress qos";
        tailf:cli-embed-no-on-delete;
        tailf:cli-sequence-commands;
        tailf:cli-compact-syntax;

        // ingress / qos / network-policy-id
        leaf network-policy-id {
          tailf:info "<network-policy-id>";
          tailf:cli-drop-node-name;
          tailf:cli-no-value-on-delete;
          type uint16;
          tailf:non-strict-leafref {
            path "/alu:qos/sap-ingress/policy-id";
          }
        }

        // ingress / qos fp-redirect-group
        leaf fp-redirect-group {
          tailf:info "<queue-group-name>";
          tailf:cli-no-name-on-delete;
          tailf:cli-no-value-on-delete;
          tailf:non-strict-leafref {
            path "/alu:qos/queue-group-templates/ingress/queue-group/"
              +"queue-group-name";
          }
          type string;
        }

        // ingress / qos instance
        leaf instance {
          tailf:info "<instance-id>";
          tailf:cli-no-name-on-delete;
          tailf:cli-no-value-on-delete;
          type uint16 {
            range "1..16384";
          }
        }
      }

      // ingress / vc-label
      leaf vc-label {
        tailf:info "Configure egress label";
        type uint32 {
          range "16..1048575";
        }
      }
    }

    // mac-pinning
    leaf mac-pinning {
      tailf:info "Enable/disable MAC address pinning";
      type empty;
    }

    // static-mac
    list static-mac {
      tailf:info "Configure a static mac entry";
      tailf:cli-embed-no-on-delete;
      tailf:cli-suppress-mode;
      key address;
      leaf address {
        type ieee-mac;
      }

      // static-mac create
      leaf create {
        tailf:cli-no-name-on-delete;
        mandatory true;
        type empty;
      }
    }

    // restrict-protected-src
    leaf restrict-protected-src {
      tailf:info "Enable/disable protected src MAC restriction";
      tailf:cli-no-value-on-delete;
      type enumeration {
        enum alarm-only;
        enum discard-frame;
      }
    }

    // vlan-vc-tag
    leaf vlan-vc-tag {
      type uint16 {
        range "0..4094";
      }
    }
  }

  // stp-common
  grouping stp-common {

    // stp / auto-edge
    leaf auto-edge {
      tailf:info "Enable/disable automatic detection of edge port";
      tailf:cli-embed-no-on-delete;
      type empty;
    }

    // stp / edge-port
    leaf edge-port {
      tailf:info "Configure spoke-sdp as edge port";
      tailf:cli-embed-no-on-delete;
      type empty;
    }

    // stp / link-type
    leaf link-type {
      tailf:info "Configure link type of the spoke-sdp";
      tailf:cli-embed-no-on-delete;
      type enumeration {
        enum pt-pt;
        enum shared;
      }
    }

    // stp / path-cost
    leaf path-cost {
      tailf:info "Configure path-cost";
      tailf:cli-no-name-on-delete;
      type uint32 {
        range "1..200000000";
      }
    }

    // stp / port-num
    leaf port-num {
      tailf:info "Configure virtual port number";
      tailf:cli-embed-no-on-delete;
      type uint16;
    }

    // stp / priority
    leaf priority {
      tailf:info "Configure stp priority";
      tailf:cli-embed-no-on-delete;
      type uint16 {
        range "4096..65535";
      }
    }

    // stp / shutdown
    leaf shutdown {
      tailf:info "Enable/disable spanning tree protocol";
      tailf:cli-boolean-no;
      default true;
      type boolean;
    }
  }


  // filter-choice
  grouping filter-choice {
    choice filter {

      // filter ip
      leaf ip {
        tailf:info "<ip-filter-id>;;[1..65535]|<name:64 char max>";
        tailf:non-strict-leafref {
          path "/alu:filter/ip-filter/ip-filter-name";
        }
        type string;
      }

      // filter ipv6
      leaf ipv6 {
        tailf:info "<ipv6-filter-id>;;[1..65535]|<name:64 char max>";
        tailf:non-strict-leafref {
          path "/alu:filter/ipv6-filter/ip-filter-name";
        }
        type string;
      }

      // filter mac
      leaf mac {
        tailf:info "<mac-filter-id>;;[1..65535]|<name:64 char max>";
        tailf:non-strict-leafref {
          path "/alu:filter/mac-filter/mac-filter-name";
        }
        type string;
      }
    }
  }

  // eth-test-enable
  grouping eth-test {

    leaf test-pattern {
      tailf:cli-embed-no-on-delete;
      type test-pattern;
    }

    leaf crc-enable {
      type empty;
      when "../test-pattern";
    }
  }


  // time-stamp
  grouping time-stamp {

    // time-stamp week
    leaf start-week {
      tailf:cli-drop-node-name;
      type enumeration {
        enum first;
        enum second;
        enum third;
        enum fourth;
        enum last;
      }
    }

    // time-stamp day
    leaf start-day {
      tailf:cli-drop-node-name;
      type enumeration {
        enum sunday;
        enum monday;
        enum tuesday;
        enum wednesday;
        enum thursday;
        enum friday;
        enum saturday;
      }
    }

    // time-stamp month
    leaf month {
      tailf:cli-drop-node-name;
      type enumeration {
        enum january;
        enum february;
        enum march;
        enum april;
        enum may;
        enum june;
        enum july;
        enum august;
        enum september;
        enum october;
        enum november;
        enum december;
      }
    }

    // time-stamp hours-minutes
    leaf hours-minutes {
      tailf:cli-drop-node-name;
      type string;
    }
  }


  // ip-filter-entry
  grouping ip-filter-entry-grouping {

    leaf entry-name {
      type string;
    }

    // filter / ip-filter * / entry * / create
    leaf create {
      mandatory true;
      type empty;
      tailf:cli-hide-in-submode;
      tailf:cli-no-name-on-delete;
    }

    // filter / ip-filter * / entry * / description
    leaf description {
      tailf:cli-no-name-on-delete;
      type string {
        length "1..80";
      }
    }

    // filter / ip-filter * / entry * / log
    leaf log {
      tailf:cli-embed-no-on-delete;
      type uint16;
    }

    // filter / ip-filter * / entry * / match /
    container match {
      tailf:cli-add-mode;

      // filter / ip-filter * / entry * / match / protocol
      leaf protocol {
        tailf:cli-hide-in-submode;
        type protocol;
      }

      // filter / ip-filter * / entry * / match / dscp
      leaf dscp {
        type dscp-type;
      }

      // filter / ip-filter * / entry * / match / src-ip
      container src-ip {
        tailf:cli-embed-no-on-delete;
        tailf:cli-compact-syntax;
        tailf:cli-sequence-commands;
        uses filter-match-ip-grouping;
      }

      // filter / ip-filter * / entry * / match / dst-ip
      container dst-ip {
        tailf:cli-embed-no-on-delete;
        tailf:cli-compact-syntax;
        tailf:cli-sequence-commands;
        uses filter-match-ip-grouping;
      }

      // filter / ip-filter * / entry * / match / icmp-type
      leaf icmp-type {
        type icmp-type;
      }

      // filter / ip-filter * / entry * / match / icmp-code
      leaf icmp-code {
        type uint32;
      }

      // filter / ip-filter * / entry * / match / fragment
      leaf fragment {
        type boolean;
      }

      // filter / ip-filter * / entry * / match / ip-option
      container ip-option {
        tailf:cli-compact-syntax;

        // filter / ip-filter * / entry * / match / ip-option a
        leaf a {
          tailf:cli-drop-node-name;
          type uint32;
        }

        // filter / ip-filter * / entry * / match / ip-option b
        leaf b {
          tailf:cli-drop-node-name;
          type uint32;
        }
      }

      // filter / ip-filter * / entry * / match / dst-port
      container dst-port {
        tailf:cli-compact-syntax;
        tailf:cli-sequence-commands;
        tailf:cli-embed-no-on-delete;

        // filter / ip-filter * / entry * / match / dst-port
        choice port-choice {
          case a {

            // filter / ip-filter * / entry * / match / dst-port op
            leaf op {
              tailf:info "operators";
              tailf:cli-drop-node-name;
              tailf:cli-no-value-on-delete;
              type enumeration {
                enum lt;
                enum gt;
                enum eq;
              }
            }

            // filter / ip-filter * / entry * / match / dst-port port
            leaf port {
              tailf:info "port number";
              tailf:cli-drop-node-name;
              tailf:cli-no-value-on-delete;
              mandatory true;
              type uint16;
            }
          }
          case b {

            // filter / ip-filter * / entry * / match / dst-port range
            leaf range {
              tailf:info "port range";
              type empty;
            }

            // filter / ip-filter * / entry * / match / dst-port +
            // range start
            leaf start {
              tailf:info "start";
              tailf:cli-drop-node-name;
              tailf:cli-no-value-on-delete;
              mandatory true;
              type uint16;
            }

            // filter / ip-filter * / entry * / match / dst-port +
            // range end
            leaf end {
              tailf:info "end";
              tailf:cli-drop-node-name;
              tailf:cli-no-value-on-delete;
              mandatory true;
              type uint16;
            }
          }
        }
      }

      // filter / ip-filter * / entry * / match / src-port
      container src-port {
        tailf:cli-compact-syntax;
        tailf:cli-sequence-commands;
        tailf:cli-embed-no-on-delete;

        // filter / ip-filter * / entry * / match / src-port
        choice port-choice {
          case a {
            // filter / ip-filter * / entry * / match / src-port +
            // port-choice op
            leaf op {
              tailf:cli-drop-node-name;
              tailf:cli-no-value-on-delete;
              type enumeration {
                enum lt;
                enum gt;
                enum eq;
              }
            }

            // filter / ip-filter * / entry * / match / src-port +
            // port-choice port
            leaf port {
              tailf:cli-drop-node-name;
              tailf:cli-no-value-on-delete;
              mandatory true;
              type uint16;
            }
          }
          case b {

            // filter / ip-filter * / entry * / match / src-port +
            // port-choice range
            leaf range {
              type empty;
            }

            // filter / ip-filter * / entry * / match / src-port +
            // port-choice start
            leaf start {
              tailf:cli-drop-node-name;
              tailf:cli-no-value-on-delete;
              mandatory true;
              type uint16;
            }

            // filter / ip-filter * / entry * / match / src-port +
            // port-choice end
            leaf end {
              tailf:cli-drop-node-name;
              tailf:cli-no-value-on-delete;
              mandatory true;
              type uint16;
            }
          }
          case c {
            // filter / ip-filter * / entry * / match / src-port
            // src-port-number
            leaf src-port-number {
              tailf:cli-drop-node-name;
              type uint16;
            }

            // filter / ip-filter * / entry * / match / src-port mask
            leaf mask {
              tailf:cli-drop-node-name;
              mandatory true;
              type uint16;
            }
          }
        }
      }
    }
  }

  // ipv6-filter-entry
  grouping ipv6-filter-entry-grouping {

    leaf entry-name {
      type string;
    }

    // filter / ipv6-filter * / entry * / create
    leaf create {
      mandatory true;
      type empty;
      tailf:cli-hide-in-submode;
      tailf:cli-no-name-on-delete;
    }

    // filter / ipv6-filter * / entry * / description
    leaf description {
      type string;
    }

    // filter / ipv6-filter * / entry * / match /
    container match {
      tailf:cli-add-mode;

      // filter / ipv6-filter * / entry * / match / next-header
      leaf next-header {
        tailf:cli-hide-in-submode;
        type enumeration {
          enum "*";
          enum "none";
          enum "icmp";
          enum "igmp";
          enum "ip";
           enum "tcp";
           enum "egp";
           enum "igp";
           enum "udp";
           enum "rdp";
           enum "ipv6";
           enum "idrp";
           enum "rsvp";
           enum "gre";
           enum "ipv6-icmp";
           enum "ipv6-no-nxt";
           enum "iso-ip";
           enum "eigrp";
           enum "ospf-igp";
           enum "ether-ip";
           enum "encap";
           enum "pnni";
           enum "pim";
           enum "vrrp";
           enum "l2tp";
           enum "stp";
           enum "ptp";
           enum "isis";
           enum "crtp";
           enum "crudp";
           enum "sctp";
        }
      }

      // filter / ipv6-filter * / entry * / match / dscp
      leaf dscp {
        type dscp-type;
      }

      // filter / ipv6-filter * / entry * / match / src-ip
      container src-ip {
        tailf:cli-embed-no-on-delete;
        tailf:cli-compact-syntax;
        tailf:cli-sequence-commands;
        uses filter-match-ipv6-grouping;
      }

      // filter / ipv6-filter * / entry * / match / dst-ip
      container dst-ip {
        tailf:cli-embed-no-on-delete;
        tailf:cli-compact-syntax;
        tailf:cli-sequence-commands;
        uses filter-match-ipv6-grouping;
      }

      // filter / ipv6-filter * / entry * / match / icmp-type
      leaf icmp-type {
        type icmpv6-type;
      }

      // filter / ipv6-filter * / entry * / match / icmp-code
      leaf icmp-code {
        type uint32;
      }

      // filter / ipv6-filter * / entry * / match / fragment
      leaf fragment {
        type boolean;
      }

      // filter / ipv6-filter * / entry * / match / ip-option
      container ip-option {
        tailf:cli-compact-syntax;

        // filter / ipv6-filter * / entry * / match / ip-option a
        leaf a {
          tailf:cli-drop-node-name;
          type uint32;
        }

        // filter / ipv6-filter * / entry * / match / ip-option b
        leaf b {
          tailf:cli-drop-node-name;
          type uint32;
        }
      }

      // filter / ipv6-filter * / entry * / match / dst-port
      container dst-port {
        tailf:cli-compact-syntax;
        tailf:cli-sequence-commands;

        // filter / ipv6-filter * / entry * / match / dst-port port-choice
        choice port-choice {
          case a {
            // filter / ipv6-filter * / entry * / match / dst-port +
            // port-choice op
            leaf op {
              tailf:cli-drop-node-name;
              type enumeration {
                enum lt;
                enum gt;
                enum eq;
              }
            }

            // filter / ipv6-filter * / entry * / match / dst-port +
            // port-choice port
            leaf port {
              tailf:cli-drop-node-name;
              type uint16;
            }
          }
          case b {

            // filter / ipv6-filter * / entry * / match / dst-port +
            // port-choice range
            leaf range {
              type empty;
            }

            // filter / ipv6-filter * / entry * / match / dst-port +
            // port-choice start
            leaf start {
              tailf:cli-drop-node-name;
              type uint16;
            }

            // filter / ipv6-filter * / entry * / match / dst-port +
            // port-choice end
            leaf end {
              tailf:cli-drop-node-name;
              type uint16;
            }
          }
        }
      }

      // filter / ipv6-filter * / entry * / match / src-port
      container src-port {
        tailf:cli-compact-syntax;
        tailf:cli-sequence-commands;

        // filter / ipv6-filter * / entry * / match / src-port port-choice
        choice port-choice {
          case a {

            // filter / ipv6-filter * / entry * / match / src-port +
            // port-choice op
            leaf op {
              tailf:cli-drop-node-name;
              type enumeration {
                enum lt;
                enum gt;
                enum eq;
              }
            }

            // filter / ipv6-filter * / entry * / match / src-port +
            // port-choice port
            leaf port {
              tailf:cli-drop-node-name;
              type uint16;
            }
          }
          case b {

            // filter / ipv6-filter * / entry * / match / src-port +
            // port-choice range
            leaf range {
              type empty;
            }

            // filter / ipv6-filter * / entry * / match / src-port +
            // port-choice start
            leaf start {
              tailf:cli-drop-node-name;
              type uint16;
            }

            // filter / ipv6-filter * / entry * / match / src-port +
            // port-choice end
            leaf end {
              tailf:cli-drop-node-name;
              type uint16;
            }
          }
        }
      }
    }
  }

  // queue-override-grouping
  grouping queue-override-grouping {

    // queue *
    list queue {
      tailf:cli-embed-no-on-delete;
      key queue-id;

      leaf queue-id {
        type uint32;
      }

      // queue * / adaption-rule
      container adaption-rule {
        tailf:cli-compact-syntax;
        tailf:cli-sequence-commands;
        tailf:cli-embed-no-on-delete;

        // queue * / adaption-rule pir
        leaf pir {
          type adaption-rule;
        }

        // queue * / adaption-rule cir
        leaf cir {
          type adaption-rule;
        }
      }

      // queue * / avg-frame-overhead
      leaf avg-frame-overhead {
        tailf:cli-embed-no-on-delete;
        type decimal64 {
          fraction-digits 2;
          range "0..100";
        }
      }

      // queue * / mbs
      container mbs {
        tailf:cli-compact-syntax;
        tailf:cli-sequence-commands;
        tailf:cli-embed-no-on-delete;

        // queue * / mbs val
        leaf val {
          tailf:cli-drop-node-name;
          type union {
            type enumeration {
              enum default;
            }
            type uint32 {
              range "0..134217728";
            }
          }
        }

        // queue * / mbs unit
        leaf unit {
          tailf:cli-drop-node-name;
          type enumeration {
            enum bytes;
            enum kilobytes;
          }
        }
      }

      // queue * / cbs
      leaf cbs {
        tailf:cli-embed-no-on-delete;
        type union {
          type enumeration {
            enum default;
          }
          type uint32 {
            range "0..131072";
          }
        }
      }

      // queue * / high-prio-only
      leaf high-prio-only {
        type union {
          type enumeration {
            enum default;
          }
          type uint8;
        }
      }

      // queue * / rate
      container rate {
        tailf:cli-compact-syntax;
        tailf:cli-sequence-commands;
        tailf:cli-embed-no-on-delete;

        // queue * / rate pir
        leaf pir {
          tailf:cli-drop-node-name;
          type union {
            type enumeration {
              enum max;
            }
            type uint32 {
              range "1..100000000";
            }
          }
        }

        // queue * / rate cir
        leaf cir {
          type union {
            type enumeration {
              enum max;
            }
            type uint32 {
              range "0..100000000";
            }
          }
        }
      }

      // queue * / parent
      container parent {
        tailf:cli-compact-syntax;
        tailf:cli-sequence-commands;
        tailf:cli-embed-no-on-delete;

        // queue * / parent weight
        leaf weight {
          type uint8 {
            range "0..100";
          }
        }

        // queue * / parent cir-weight
        leaf cir-weight {
          type uint8 {
            range "0..100";
          }
        }
      }

      // queue * / percent-rate
      container percent-rate {
        tailf:cli-compact-syntax;
        tailf:cli-sequence-commands;
        tailf:cli-embed-no-on-delete;

        // queue * / percent-rate pir
        leaf pir {
          tailf:cli-drop-node-name;
          type decimal64 {
            fraction-digits 2;
            range "0..100";
          }
        }

        // queue * / percent-rate cir
        leaf cir {
          type decimal64 {
            fraction-digits 2;
            range "0..100";
          }
        }
      }

      // queue * create
      leaf create {
        mandatory true;
        type empty;
        tailf:cli-hide-in-submode;
        tailf:cli-no-name-on-delete;
      }
    }
  }

  grouping ip-criteria-grouping {

    leaf match-criteria {
      tailf:cli-hide-in-submode;
      tailf:cli-drop-node-name;
      tailf:cli-no-value-on-delete;
      type enumeration {
        enum any;
        enum dscp-only;
      }
    }

    list entry {
      key id;
      leaf id {
        type uint16;
      }

      leaf create {
        mandatory true;
        type empty;
        tailf:cli-hide-in-submode;
        tailf:cli-no-name-on-delete;
      }

      leaf description {
        tailf:cli-embed-no-on-delete;
        type string;
      }

      container match {
        tailf:cli-add-mode;
        leaf protocol {
          tailf:cli-hide-in-submode;
          type protocol;
        }
        leaf dscp {
          type string;
        }
        leaf dst-ip {
          type tailf:ipv4-address-and-prefix-length;
        }
        leaf src-ip {
          type tailf:ipv4-address-and-prefix-length;
        }
        container dst-port {
          tailf:cli-compact-syntax;
          tailf:cli-sequence-commands;
          choice port-choice {
            case a {
              leaf op {
                tailf:cli-drop-node-name;
                type enumeration {
                  enum lt;
                  enum gt;
                  enum eq;
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
        container src-port {
          tailf:cli-compact-syntax;
          tailf:cli-sequence-commands;
          choice port-choice {
            case a {
              leaf op {
                tailf:cli-drop-node-name;
                type enumeration {
                  enum lt;
                  enum gt;
                  enum eq;
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
      }
      container action {
        tailf:cli-compact-syntax;
        leaf fc {
          type string;
        }
        leaf priority {
          type enumeration {
            enum high;
            enum low;
          }
        }
      }
    }
  }

  // ipv6-criteria-grouping
  grouping ipv6-criteria-grouping {

    list entry {
      key id;
      leaf id {
        type uint16;
      }

      leaf create {
        mandatory true;
        type empty;
        tailf:cli-hide-in-submode;
        tailf:cli-no-name-on-delete;
      }

      leaf description {
        type string;
      }

      container match {
        tailf:cli-add-mode;
        leaf protocol {
          tailf:cli-hide-in-submode;
          type protocol;
        }
        leaf dst-ip {
          type tailf:ipv6-address-and-prefix-length;
        }
        leaf src-ip {
          type tailf:ipv6-address-and-prefix-length;
        }
        container dst-port {
          tailf:cli-compact-syntax;
          tailf:cli-sequence-commands;
          choice port-choice {
            case a {
              leaf op {
                tailf:cli-drop-node-name;
                type enumeration {
                  enum lt;
                  enum gt;
                  enum eq;
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
        container src-port {
          tailf:cli-compact-syntax;
          tailf:cli-sequence-commands;
          choice port-choice {
            case a {
              leaf op {
                tailf:cli-drop-node-name;
                type enumeration {
                  enum lt;
                  enum gt;
                  enum eq;
                }
              }
              leaf port {
                tailf:cli-drop-node-name;
                type uint16;
              }
            }
            case b {
              leaf range {
                type empty;
              }
              leaf start {
                tailf:cli-drop-node-name;
                type uint16;
              }
              leaf end {
                tailf:cli-drop-node-name;
                type uint16;
              }
            }
          }
        }
      }
      container action {
        tailf:cli-compact-syntax;
        leaf fc {
          type string;
        }
        leaf priority {
          type enumeration {
            enum high;
            enum low;
          }
        }
      }
    }
  }

  // meter-grouping
  grouping meter-grouping {

    leaf meter-id {
      type uint8 {
        range "1..32";
      }
    }

    leaf multipoint {
      tailf:cli-hide-in-submode;
      tailf:cli-no-name-on-delete;
      type empty;
    }

    container adaptation-rule {
      tailf:info "Specify the CIR and PIR adaptation rules";
      tailf:cli-embed-no-on-delete;
      tailf:cli-compact-syntax;
      leaf cir {
        tailf:cli-no-name-on-delete;
        tailf:cli-no-value-on-delete;
        type enumeration {
          enum max;
          enum min;
          enum closest;
        }
      }

      leaf pir {
        tailf:cli-no-name-on-delete;
        tailf:cli-no-value-on-delete;
        type enumeration {
          enum max;
          enum min;
          enum closest;
        }
      }
    }

    container cbs {
      tailf:info "Specify CBS";
      tailf:cli-compact-syntax;
      leaf size {
        tailf:cli-drop-node-name;
        tailf:cli-no-value-on-delete;
        type union {
          type uint32 {
            range "4..2146959";
          }
          type enumeration {
            enum default;
          }
        }
      }
    }

    container mbs {
      tailf:info "Specify MBS";
      tailf:cli-compact-syntax;
      leaf size {
        tailf:cli-drop-node-name;
        tailf:cli-no-value-on-delete;
        type union {
          type uint32 {
            range "4..2146959";
          }
          type enumeration {
            enum default;
          }
        }
      }
    }

    container rate {
      tailf:info "Specify rates (CIR and PIR)";
      tailf:cli-compact-syntax;
      tailf:cli-embed-no-on-delete;
      leaf pir {
        tailf:cli-no-value-on-delete;
        type union {
          type uint32{
            range "0..20000000";
          }
          type enumeration {
            enum max;
          }
        }
      }

      leaf cir {
        tailf:cli-no-value-on-delete;
        type union {
          type uint32 {
            range "0..20000000";
          }
          type enumeration {
            enum max;
          }
        }
      }
    }

    leaf mode {
      tailf:info "Specify rate mode";
      type enumeration {
        enum trtcm1;
        enum trtcm2;
        enum srtcm;
      }
    }

    leaf create {
      tailf:cli-hide-in-submode;
      tailf:cli-no-name-on-delete;
      mandatory true;
      type empty;
    }
  }

  grouping cpm-filter-match-port-grouping {
    choice port-choice {
      case a {
        // Use port + mask
        leaf port-number {
          tailf:info "<tcp/udp port-number>";
          tailf:cli-drop-node-name;
          tailf:cli-no-value-on-delete;
          type uint16;
        }

        leaf mask {
          tailf:info "<tcp/udp port mask>";
          tailf:cli-drop-node-name;
          tailf:cli-no-value-on-delete;
          type uint16;
        }
      }
      case b {
        // Use port range: start end
        leaf range {
          tailf:info "range <tcp/udp port-number> <tcp/udp port-number>";
          type empty;
        }
        leaf start {
          tailf:cli-drop-node-name;
          type uint16;
        }
        leaf end {
          tailf:cli-drop-node-name;
          type uint16;
        }
      }
      case c {
        // Use port list
        leaf port-list {
          tailf:info "port-list <port-list-name>";
          type string {
            length "1..32";
          }
        }
      }
    }
  }

  //  filter-match-ip-grouping
  grouping filter-match-ip-grouping {
    choice ip {
      leaf address {
        tailf:info "<ip-address/prefix-length> | <ip-address>";
        tailf:cli-drop-node-name;
        tailf:cli-no-value-on-delete;
        type union {
          type inet:ipv4-address;
          type inet:ipv4-prefix;
          type string;
        }
      }
      leaf ip-prefix-list {
        tailf:info "ip-prefix-list <prefix-list-name>";
        tailf:cli-no-value-on-delete;
        tailf:cli-no-name-on-delete;
        type string;
      }
    }
  }


  //  filter-match-ipv6-grouping
  grouping filter-match-ipv6-grouping {
    choice ipv6 {
      leaf address {
        tailf:info "<ipv6-address/prefix-length> | <ipv6-address>";
        tailf:cli-drop-node-name;
        tailf:cli-no-value-on-delete;
        type union {
          type tailf:ipv6-address-and-prefix-length;
          type inet:ipv6-address;
          type string;
        }
      }
      leaf ipv6-prefix-list {
        tailf:info "ipv6-prefix-list <prefix-list-name>";
        tailf:cli-no-value-on-delete;
        tailf:cli-no-name-on-delete;
        type string;
      }
    }
  }

  grouping sap-egress-grouping {
    // sap * / egress / agg-rate-limit
    leaf  agg-rate-limit {
      tailf:cli-embed-no-on-delete;
      tailf:cli-no-value-on-delete;
      type uint32 {
        range "1..40000000";
      }
    }

    // sap * / egress / filter
    container filter {
      tailf:cli-embed-no-on-delete;
      uses filter-choice;
    }

    // sap  * / egress / multicast-group
    leaf multicast-group {
      tailf:cli-embed-no-on-delete;
      tailf:cli-no-value-on-delete;
      type string;
    }

    // sap  * / egress / qos
    leaf qos {
      tailf:info "Apply egress qos policy";
      tailf:cli-embed-no-on-delete;
      tailf:cli-no-value-on-delete;
      type uint16;
      tailf:non-strict-leafref {
        path "/alu:qos/sap-egress/policy-id";
      }
    }

    // sap  * / egress / scheduler-policy
    leaf scheduler-policy {
      tailf:info "Specify a scheduler policy";
      tailf:cli-embed-no-on-delete;
      tailf:cli-no-value-on-delete;
      tailf:cli-diff-dependency "../../multi-service-site" {
        tailf:cli-trigger-on-set;
      }
      tailf:non-strict-leafref {
        path "/alu:qos/scheduler-policy/scheduler-policy-name";
      }
      type string;
    }

    // sap  * / egress / scheduler-override
    container scheduler-override {
      tailf:info "Apply a scheduler override";
      tailf:cli-add-mode;

      leaf scheduler {
        tailf:cli-embed-no-on-delete;
        tailf:cli-no-value-on-delete;
        tailf:non-strict-leafref {
          path "/alu:qos/scheduler-policy/scheduler-policy-name";
        }
        type string;
      }
    }

    // sap  * / egress / qinq-mark-top-only
    leaf qinq-mark-top-only {
      tailf:info "Mark p-bits on top q-tag only";
      type empty;
    }
  }

  grouping sap-ingress-grouping {
    // sap * / ingress filter
    container filter {
      tailf:cli-embed-no-on-delete;
      uses filter-choice;
    }

    // sap  * / ingress / match-qinq-dot1p
    leaf match-qinq-dot1p {
      tailf:info "Define 802.1P bits to match in QinQ SAP's";
      tailf:cli-embed-no-on-delete;
      tailf:cli-no-value-on-delete;

      type enumeration {
        enum top;
        enum bottom;
      }
    }

    // sap  * / ingress / qos
    leaf qos {
      tailf:info "Apply ingress qos policy";
      tailf:cli-embed-no-on-delete;
      tailf:cli-no-value-on-delete;
      type uint16;
      tailf:non-strict-leafref {
        path "/alu:qos/sap-ingress/policy-id";
      }
    }

    // sap  * / ingress / scheduler-policy
    leaf scheduler-policy {
      tailf:info "Specify a scheduler-policy";
      tailf:cli-embed-no-on-delete;
      tailf:cli-no-value-on-delete;
      tailf:non-strict-leafref {
        path "/alu:qos/scheduler-policy/scheduler-policy-name";
      }
      type string;
    }

    // sap  * / ingress / scheduler-override
    container scheduler-override {
      tailf:info "Apply a scheduler override";
      tailf:cli-add-mode;

      leaf scheduler {
        tailf:cli-embed-no-on-delete;
        tailf:cli-no-value-on-delete;
        tailf:non-strict-leafref {
          path "/alu:qos/scheduler-policy/scheduler-policy-name";
        }
        type string;
      }
    }

    // sap  * / ingress / vlan-translation
    leaf vlan-translation {
      tailf:info "Apply Ingress Vlan Translation";
      tailf:cli-embed-no-on-delete;
      tailf:cli-no-value-on-delete;

      type union {
        type enumeration {
          enum copy-outer;
        }
        type uint16 {
          range "0..4094";
        }
      }
    }
  }

  // policy-options-action-grouping
  grouping policy-options-action-grouping {
    choice action {
      leaf reject {
        tailf:cli-no-name-on-delete;
        type empty;
      }
      container other {
        tailf:cli-add-mode;
        tailf:cli-drop-node-name;
        tailf:cli-sequence-commands;
        leaf action {
          tailf:cli-hide-in-submode;
          tailf:cli-drop-node-name;
          type enumeration {
            enum accept;
            enum next-entry;
            enum next-policy;
          }
        }
        leaf aigp-metric {
          tailf:info "Assign a BGP AIGP metric to routes matching the entry";
          tailf:cli-no-value-on-delete;
          tailf:cli-break-sequence-commands;
          type uint32 {
            range "0..4294967295";
          }
        }
        container as-path {
          tailf:info "Assign a BGP AS Path list to routes that do not match";
          tailf:cli-embed-no-on-delete;
          tailf:cli-compact-syntax;
          tailf:cli-sequence-commands;
          leaf action {
            tailf:cli-drop-node-name;
            tailf:cli-no-value-on-delete;
            type enumeration {
              enum add;
              enum replace;
            }
          }
          leaf name {
            tailf:cli-drop-node-name;
            tailf:cli-no-value-on-delete;
            type string {
              length "1..32";
            }
          }
        }
        container  as-path-prepend {
          tailf:info "Prepending a BGP AS number to the AS Path attribute
                              of routes that do not match any entry";
          tailf:cli-embed-no-on-delete;
          tailf:cli-compact-syntax;
          tailf:cli-sequence-commands;
          leaf as-number {
            tailf:cli-drop-node-name;
            tailf:cli-no-value-on-delete;
            type uint32 {
              range "1..4294967295";
            }
          }
          leaf repeat {
            tailf:cli-drop-node-name;
            tailf:cli-no-value-on-delete;
            type uint8 {
              range "1..50";
            }
          }
        }
        container community {
          tailf:info "Apply a BGP community list to routes that do not match
                              any entry";
          tailf:cli-embed-no-on-delete;
          tailf:cli-compact-syntax;
          tailf:cli-sequence-commands;
          leaf action {
            tailf:cli-drop-node-name;
            tailf:cli-no-value-on-delete;
            type enumeration {
              enum add;
              enum remove;
              enum replace;
            }
          }
          leaf name {
            tailf:cli-drop-node-name;
            tailf:cli-no-value-on-delete;
            type string {
              length "1..32";
            }
          }
        }
        container damping {
          tailf:info "Configure a damping profile to be used for routes that
                              do not match any entry";
          choice damping {
            leaf none {
              tailf:cli-no-name-on-delete;
              type empty;
            }
            leaf name {
              tailf:cli-drop-node-name;
              tailf:cli-no-value-on-delete;
              tailf:non-strict-leafref {
                path "/alu:router/policy-options/begin/damping/name";
              }
              type string;
            }
          }
        }
        leaf local-preference {
          tailf:info "Assign a BGP Local Preference to routes that do not
                              match any entry";
          tailf:cli-no-value-on-delete;
          type uint32 {
            range "0..4294967295";
          }
        }
        container metric {
          tailf:info "Assign a metric to routes that do not match any entry";
          tailf:cli-embed-no-on-delete;
          tailf:cli-compact-syntax;
          tailf:cli-sequence-commands;
          leaf action {
            tailf:cli-drop-node-name;
            tailf:cli-no-value-on-delete;
            tailf:cli-incomplete-command;
            type enumeration {
              enum add;
              enum set;
              enum subtract;
            }
          }
          leaf metric {
            tailf:cli-drop-node-name;
            tailf:cli-no-value-on-delete;
            type union {
              type enumeration {
                enum igp;
              }
              type uint32 {
                range "0..4294967295";
              }
            }
          }
        }
        container multicast-redirect {
          tailf:info "Configure the interface where to redirect IGMP
                              multicast traffic to";
          tailf:cli-embed-no-on-delete;
          tailf:cli-compact-syntax;
          tailf:cli-sequence-commands;

          leaf fwd-service {
            tailf:cli-no-name-on-delete;
            tailf:cli-no-value-on-delete;
            type uint32 {
              range "1..2147483650";
            }
          }
          leaf ip-int-name {
            tailf:cli-drop-node-name;
            tailf:cli-no-value-on-delete;
            type string {
              length "1..32";
            }
          }
        }
        leaf next-hop {
          tailf:info "Assign a next hop IP address to routes that do not
                              match any entry";
          tailf:cli-no-value-on-delete;
          type inet:ipv4-address;
        }
        leaf next-hop-self {
          tailf:info "Advertising a next hop IP address belonging to this
                              router to routes that do not match any entry";
          type empty;
        }

        leaf origin {
          tailf:info "Set the BGP origin assigned to routes exported into
                              BGP that do not match any entry";
          tailf:cli-no-value-on-delete;
          type enumeration {
            enum igp;
            enum egp;
            enum incomplete;
          }
        }

        leaf preference {
          tailf:info "Assign a route preference to routes that do not
                              match any entry";
          tailf:cli-no-value-on-delete;
          type uint8 {
            range "1..255";
          }
        }

        leaf tag {
          tailf:info "Assign an OSPF RIP or ISIS tag to routes that do
                              not match any entry";
          tailf:cli-no-value-on-delete;
          type string;
        }

        leaf type {
          tailf:info "Assign an OSPF type metric to routes that do not
                              match any entry";
          tailf:cli-no-value-on-delete;
          type uint8 {
            range "1..2";
          }
        }
      }
    }
  }

  // queue-group-template-entry
  grouping queue-group-template-entry {

    // queue-group-template-entry / queue-group-name
    leaf queue-group-name {
      type string;
    }

    // queue-group-template-entry / create
    leaf create {
      tailf:cli-hide-in-submode;
      tailf:cli-no-name-on-delete;
      mandatory true;
      type empty;
    }

    // queue-group-template-entry / description
    leaf description {
      tailf:info "Configure description for the QoS queue-group";
      type string;
    }

    // queue-group-template-entry / fc *
    list fc {
      tailf:info "Configure forwarding-class to queue mappings";
      tailf:cli-embed-no-on-delete;
      key fc-name;
      leaf fc-name {
        type enumeration {
          enum be;
          enum l2;
          enum af;
          enum l1;
          enum h2;
          enum ef;
          enum h1;
          enum nc;
        }
      }

      // queue-group-template-entry / fc * create
      leaf create {
        tailf:cli-hide-in-submode;
        tailf:cli-no-name-on-delete;
        mandatory true;
        type empty;
      }

      // queue-group-template-entry / fc * / queue
      leaf queue {
        tailf:info "Specify the unicast-queue";
        tailf:cli-no-value-on-delete;
        tailf:non-strict-leafref {
          path "../../queue/queue-id";
        }
        type uint8;
      }
    }

    // queue-group-template-entry / policer *
    list policer {
      tailf:info "Configure QoS queue-group policer";
      key policer-id;
      leaf policer-id {
        type uint8 {
          range "1..8";
        }
      }

      // queue-group-template-entry / policer * create
      leaf create {
        tailf:cli-hide-in-submode;
        tailf:cli-no-name-on-delete;
        mandatory true;
        type empty;
      }

      // queue-group-template-entry / policer * / adaption-rule
      container adaptation-rule {
        tailf:info "Specify the CIR and PIR adaptation rules";
        tailf:cli-embed-no-on-delete;
        tailf:cli-compact-syntax;

        leaf pir {
          tailf:info "<pir adaption-rule>";
          tailf:cli-no-name-on-delete;
          tailf:cli-no-value-on-delete;
          type enumeration {
            enum max;
            enum min;
            enum closest;
          }
        }

        leaf cir {
          tailf:info "<cir adaption-rule>";
          tailf:cli-no-name-on-delete;
          tailf:cli-no-value-on-delete;
          type enumeration {
            enum max;
            enum min;
            enum closest;
          }
        }
      }

      // queue-group-template-entry / policer * / adv-config-policy
      leaf adv-config-policy {
        tailf:info "Configure advanced configuration policy";
        tailf:cli-no-value-on-delete;
        type string {
          length "1..32";
        }
      }

      // queue-group-template-entry / policer * / cbs
      container cbs {
        tailf:info "Specify CBS";
        tailf:cli-embed-no-on-delete;
        tailf:cli-compact-syntax;
        tailf:cli-sequence-commands;

        leaf size {
          tailf:cli-drop-node-name;
          tailf:cli-no-value-on-delete;
          type union {
            type uint32 {
              range "0..4194304";
            }
            type enumeration {
              enum default;
            }
          }
        }

        leaf unit {
          tailf:cli-drop-node-name;
          tailf:cli-no-value-on-delete;
          type enumeration {
            enum bytes;
            enum kilobytes;
          }
        }
      }

      // queue-group-template-entry / policer * description
      leaf description {
        tailf:info "Configure description for the QoS queue-group policer";
        tailf:cli-no-value-on-delete;
        type string;
      }

      // queue-group-template-entry / policer * / high-prio-only
      leaf high-prio-only {
        tailf:info "Specify high priority only percent-of-mbs";
        tailf:cli-no-value-on-delete;
        type union {
          type uint8 {
            range "0..100";
          }
          type enumeration {
            enum default;
          }
        }
      }

      // queue-group-template-entry / policer * / mbs
      container mbs {
        tailf:info "Specify MBS";
        tailf:cli-embed-no-on-delete;
        tailf:cli-compact-syntax;
        tailf:cli-sequence-commands;

        leaf size {
          tailf:cli-drop-node-name;
          tailf:cli-no-value-on-delete;
          type union {
            type uint32 {
              range "0..4194304";
            }
            type enumeration {
              enum default;
            }
          }
        }

        leaf unit {
          tailf:cli-drop-node-name;
          tailf:cli-no-value-on-delete;
          type enumeration {
            enum bytes;
            enum kilobytes;
          }
        }
      }

      // queue-group-template-entry / policer * / packet-byte-offset
      container packet-byte-offset {
        tailf:info "Specify packet byte offset";
        tailf:cli-embed-no-on-delete;
        tailf:cli-compact-syntax;

        choice add-delete {
          leaf add {
            tailf:cli-no-name-on-delete;
            tailf:cli-no-value-on-delete;
            type uint8 {
              range "0..31";
            }
          }

          leaf subtract {
            tailf:cli-no-name-on-delete;
            tailf:cli-no-value-on-delete;
            type uint8 {
              range "1..32";
            }
          }
        }
      }

      // queue-group-template-entry / policer * / parent
      container parent {
        tailf:info "Specify the scheduler to which this policer feeds";
        tailf:cli-embed-no-on-delete;
        tailf:cli-compact-syntax;
        tailf:cli-sequence-commands;

        leaf name {
          tailf:cli-drop-node-name;
          tailf:cli-no-value-on-delete;
          type union {
            type string;
            type enumeration {
              enum root;
            }
          }
        }

        leaf level {
          tailf:cli-no-name-on-delete;
          tailf:cli-no-value-on-delete;
          type uint8 {
            range "1..8";
          }
        }

        leaf weight-level {
          tailf:cli-no-name-on-delete;
          tailf:cli-no-value-on-delete;
          type uint8 {
            range "1..100";
          }
        }
      }

      // queue-group-template-entry / policer * / profile-capped
      leaf profile-capped {
        tailf:info "Configure Profile Cap";
        type empty;
      }

      // queue-group-template-entry / policer * / rate
      container rate {
        tailf:info "Specify rates (CIR and PIR)";
        tailf:cli-embed-no-on-delete;
        tailf:cli-compact-syntax;
        tailf:cli-sequence-commands;

        leaf pir {
          tailf:cli-drop-node-name;
          tailf:cli-no-value-on-delete;
          type union {
            type uint32 {
              range "1..20000000";
            }
            type enumeration {
              enum max;
            }
          }
        }

        leaf cir {
          tailf:cli-no-name-on-delete;
          tailf:cli-no-value-on-delete;
          type union {
            type uint32 {
              range "1..20000000";
            }
            type enumeration {
              enum max;
            }
          }
        }
      }

      // queue-group-template-entry / policer * / stat-mode
      leaf stat-mode {
        tailf:info "Specify Stat Mode for the policer";
        tailf:cli-no-value-on-delete;
        type enumeration {
          enum no-stats;
          enum minimal;
          enum offered-profile-no-cir;
          enum offered-profile-cir;
          enum offered-total-cir;
          enum offered-limited-capped-cir;
          enum offered-profile-capped-cir;
        }
      }
    }

    // queue-group-template-entry / queue *
    list queue {
      tailf:info "Configure a queue";
      tailf:cli-embed-no-on-delete;
      key queue-id;
      leaf queue-id {
        type uint8 {
          range "1..8";
        }
      }

      // queue-group-template-entry / queue * create
      leaf create {
        tailf:cli-hide-in-submode;
        tailf:cli-no-name-on-delete;
        mandatory true;
        type empty;
      }

      // queue-group-template-entry / queue * / adaption-rule
      container adaptation-rule {
        tailf:info "Specify the CIR and PIR adaptation rules";
        tailf:cli-embed-no-on-delete;
        tailf:cli-compact-syntax;

        leaf pir {
          tailf:info "<pir adaption-rule>";
          tailf:cli-no-name-on-delete;
          tailf:cli-no-value-on-delete;
          type enumeration {
            enum max;
            enum min;
            enum closest;
          }
        }

        leaf cir {
          tailf:info "<cir adaption-rule>";
          tailf:cli-no-name-on-delete;
          tailf:cli-no-value-on-delete;
          type enumeration {
            enum max;
            enum min;
            enum closest;
          }
        }
      }

      // queue-group-template-entry / queue * / adv-config-policy
      leaf adv-config-policy {
        tailf:info "Configure advanced configuration policy";
        tailf:cli-no-value-on-delete;
        type string {
          length "1..32";
        }
      }

      // queue-group-template-entry / queue * / burst-limit
      leaf burst-limit {
        tailf:info "Specify Burst limit";
        tailf:cli-no-value-on-delete;
        type union {
          type uint32 {
            range "1..14000000";
          }
          type enumeration {
            enum default;
          }
        }
      }

      // queue-group-template-entry / queue * / cbs
      leaf cbs {
        tailf:info "Specify CBS rate";
        tailf:cli-no-value-on-delete;
        type union {
          type uint32 {
            range "0..131072";
          }
          type enumeration {
            enum default;
          }
        }
      }

      // queue-group-template-entry / queue * / high-prio-only
      leaf high-prio-only {
        tailf:info "Specify high priority only burst size";
        tailf:cli-no-value-on-delete;
        type union {
          type uint8 {
            range "0..100";
          }
        }
      }

      // queue-group-template-entry / queue * / mbs
      leaf mbs {
        tailf:info "Specify MBS rate";
        tailf:cli-no-value-on-delete;
        type union {
          type uint32 {
            range "0..134217728";
          }
          type enumeration {
            enum default;
          }
        }
      }

      // queue-group-template-entry / queue * / parent
      container parent {
        tailf:info "Specify the scheduler to which this queue feeds";
        tailf:cli-embed-no-on-delete;
        tailf:cli-compact-syntax;
        tailf:cli-sequence-commands;

        leaf name {
          tailf:cli-drop-node-name;
          tailf:cli-no-value-on-delete;
          type string {
            length "1..32";
          }
        }

        leaf weight {
          tailf:cli-no-name-on-delete;
          tailf:cli-no-value-on-delete;
          type uint8 {
            range "0..100";
          }
        }

        leaf level {
          tailf:cli-no-name-on-delete;
          tailf:cli-no-value-on-delete;
          type uint8 {
            range "1..8";
          }
        }

        leaf cir-weight {
          tailf:cli-no-name-on-delete;
          tailf:cli-no-value-on-delete;
          type uint8 {
            range "0..100";
          }
        }

        leaf cir-level {
          tailf:cli-no-name-on-delete;
          tailf:cli-no-value-on-delete;
          type uint8 {
            range "0..8";
          }
        }
      }

      // queue-group-template-entry / queue * / percent-rate
      container percent-rate {
        tailf:info "Specify Percent rates (CIR and PIR)";
        tailf:cli-embed-no-on-delete;
        tailf:cli-compact-syntax;
        tailf:cli-sequence-commands;

        leaf pir-percent {
          tailf:cli-drop-node-name;
          tailf:cli-no-value-on-delete;
          type decimal64 {
            fraction-digits 2;
            range "0.01..100.00";
          }
        }

        leaf cir {
          tailf:cli-no-name-on-delete;
          tailf:cli-no-value-on-delete;
          type decimal64 {
            fraction-digits 2;
            range "0.00..100.00";
          }
        }
      }

      // queue-group-template-entry / queue * / pool
      leaf pool {
        tailf:info "Configure named pool for this queue";
        tailf:cli-no-value-on-delete;
        type string;
      }

      // queue-group-template-entry / queue * / port-parent
      container port-parent {
        tailf:info "Specify the port-scheduler to which this queue feeds";
        tailf:cli-embed-no-on-delete;
        tailf:cli-compact-syntax;
        tailf:cli-sequence-commands;

        leaf weight {
          tailf:cli-no-name-on-delete;
          tailf:cli-no-value-on-delete;
          type uint8 {
            range "0..100";
          }
        }

        leaf level {
          tailf:cli-no-name-on-delete;
          tailf:cli-no-value-on-delete;
          type uint8 {
            range "1..8";
          }
        }

        leaf cir-weight {
          tailf:cli-no-name-on-delete;
          tailf:cli-no-value-on-delete;
          type uint8 {
            range "0..100";
          }
        }

        leaf cir-level {
          tailf:cli-no-name-on-delete;
          tailf:cli-no-value-on-delete;
          type uint8 {
            range "0..8";
          }
        }
      }

      // queue-group-template-entry / queue * / rate
      container rate {
        tailf:info "Specify rates (CIR and PIR)";
        tailf:cli-embed-no-on-delete;
        tailf:cli-compact-syntax;
        tailf:cli-sequence-commands;

        leaf pir {
          tailf:cli-drop-node-name;
          tailf:cli-no-value-on-delete;
          type union {
            type uint32 {
              range "1..10000000";
            }
            type enumeration {
              enum max;
            }
          }
        }

        leaf cir {
          tailf:cli-no-name-on-delete;
          tailf:cli-no-value-on-delete;
          type union {
            type uint32 {
              range "0..10000000";
            }
            type enumeration {
              enum max;
            }
          }
        }
      }
    }
  }

  grouping dhcp-lease-time {
    leaf days{
      tailf:cli-no-name-on-delete;
      tailf:cli-no-value-on-delete;
      type uint16 {
        range "0..3650";
      }
    }
    leaf hrs {
      tailf:cli-no-name-on-delete;
      tailf:cli-no-value-on-delete;
      type uint16 {
        range "0..23";
      }
    }
    leaf min {
      tailf:cli-no-name-on-delete;
      tailf:cli-no-value-on-delete;
      type uint16 {
        range "0..59";
      }
    }
    leaf sec {
      tailf:cli-no-name-on-delete;
      tailf:cli-no-value-on-delete;
      type uint16 {
        range "0..59";
      }
    }
  }

  /// ========================================================================
  /// card
  /// ========================================================================
  list card {
    tailf:info "Configure an I/O module in a specified slot";
    tailf:cli-recursive-delete;
    tailf:cli-embed-no-on-delete;
    key slot-number;
    leaf slot-number {
      type string;
    }
    leaf card-type {
      tailf:info "Add/remove an I/O module to/from the device";
      tailf:cli-no-value-on-delete;
      type string;
    }
    leaf fail-on-error {
      tailf:info "Configure the behavior of card-state upon errors detected";
      type empty;
    }
    // card * / mda *
    list mda {
      tailf:info "Configure a media dependant adapter";
      tailf:cli-embed-no-on-delete;
      key mda-slot;
      leaf mda-slot {
        type string;
      }
      leaf mda-type {
        tailf:info "Provisions/de-provisions an MDA to/from the device";
        tailf:cli-no-value-on-delete;
        type string;
      }
      // card * / mda * / access
      container access {
        tailf:info "Configure access MDA parameters";
        tailf:cli-add-mode;
        // card * / mda * / access / ingress
        container ingress {
          tailf:info "Configure access ingress MDA parameters";
          tailf:cli-add-mode;
          // card * / mda * / access / ingress / fabric-policy
          leaf fabric-policy {
            tailf:info "Configure the network policy";
            tailf:cli-no-value-on-delete;
            tailf:non-strict-leafref {
              path "/alu:qos/fabric-profile/policy-id";
            }
            type uint16;
          }
        }
      }
      // card * / mda * / network
      container network {
        tailf:info "Configure network MDA parameters";
        tailf:cli-add-mode;
        // card * / mda * / network / ingress
        container ingress {
          tailf:info "Configure network ingress MDA parameters";
          tailf:cli-add-mode;
          // card * / mda * / network / ingress / fabric-policy
          leaf fabric-policy {
            tailf:info "Configure the network policy";
            tailf:cli-no-value-on-delete;
            tailf:non-strict-leafref {
              path "/alu:qos/fabric-profile/policy-id";
            }
            type uint16;
          }
          // card * / mda * / network / ingress / pool
          container pool {
            tailf:info "Configure the ingress pool policy for the MDA";
            tailf:cli-add-mode;
            // card * / mda / network / ingress / pool / slope-policy
            leaf slope-policy {
              tailf:info "Configure the slope policy";
              tailf:cli-no-value-on-delete;
              type string {
                length "1..32";
              }
            }
          }
          // card * / mda * / network / queue-policy
          leaf queue-policy {
            tailf:info "Configure the network policy";
            type string;
          }
        }
      }
      leaf shutdown {
        tailf:cli-boolean-no;
        default false;
        type boolean;
      }
    }
    list fp {
      key id;
      leaf id {
        type uint32;
      }
      container ingress {
        tailf:cli-add-mode;
        container mcast-path-management {
          tailf:cli-add-mode;
          leaf bandwidth-policy {
            type string;
          }
          leaf shutdown {
            tailf:cli-boolean-no;
            default true;
            type boolean;
          }
        }
      }
    }
    leaf shutdown {
      tailf:cli-boolean-no;
      default false;
      type boolean;
    }
  }

  /// ========================================================================
  /// cflowd /
  /// ========================================================================
  container cflowd {
    presence present;
    tailf:info "Configure CFlowd";
    tailf:cli-add-mode;
    // cflowd / active-timeout
    leaf active-timeout {
      tailf:cli-no-value-on-delete;
      tailf:info "Cflowd active timeout";
      type uint16 {
        range "1..600";
      }
    }
    // cflowd / cache-size
    leaf cache-size {
      tailf:cli-no-value-on-delete;
      tailf:info "Configure maximum number of flows in the Cflowd "+
        "cache table";
      type uint32;
    }
    // cflowd / cache-size / collector *
    list collector {
      tailf:info "Configure a Cflowd data collector";
      key collector-id;
      leaf collector-id {
        tailf:cli-drop-node-name;
        type union {
          type inet:ipv4-address;
          type inet:ipv6-address;
        }
      }
      // cflowd / cache-size / collector * version
      leaf version {
        tailf:cli-hide-in-submode;
        tailf:cli-no-name-on-delete;
        tailf:cli-no-value-on-delete;
        type enumeration {
          enum "5";
          enum "8";
          enum "9";
          enum "10";
        }
      }
      // cflowd / cache-size / collector * / description
      leaf description {
        tailf:info "Configure description for this Cflowd collector";
        tailf:cli-no-value-on-delete;
        type string {
          length "1..80";
        }
      }
      // cflowd / cache-size / collector * / template-set
      leaf template-set {
        tailf:info "Configure the template set for this Cflowd collector";
        tailf:cli-no-name-on-delete;
        tailf:cli-no-value-on-delete;
        when "../version='9' or ../version='10'" {
          tailf:dependency "../version";
        }
        type enumeration {
          enum "basic";
          enum "mpls-ip";
        }
      }
      // cflowd / cache-size / collector * / autonomous-system-type
      leaf autonomous-system-type {
        tailf:info "Configures AS information based on origination or "+
          "external peer AS routes";
        tailf:cli-no-name-on-delete;
        tailf:cli-no-value-on-delete;
        when "../version='5'";
        type enumeration {
          enum "origin";
          enum "peer";
        }
      }
      // cflowd / cache-size / collector * / shutdown
      leaf shutdown {
        tailf:info "Configure description for this Cflowd collector";
        type empty;
      }
    }
    // cflowd / export-mode
    leaf export-mode {
      tailf:info "Configure Cflowd Export Mode";
      tailf:cli-no-value-on-delete;
      tailf:cli-no-name-on-delete;
      type enumeration {
        enum "automatic";
        enum "manual";
      }
      default "automatic";
    }
    // cflowd / inactive-timeout
    leaf inactive-timeout {
      tailf:info "Configure Cflowd inactive timeout";
      tailf:cli-no-value-on-delete;
      type uint16 {
        range "10..600";
      }
    }
    // cflowd / overflow
    leaf overflow {
      tailf:info "Configure percentage of entries to be removed from "+
        "Cflowd cache when the maximum number of entries has "+
        "been exceeded";
      tailf:cli-no-value-on-delete;
      type uint8 {
        range "1..50";
      }
    }
    // cflowd / rate
    leaf rate {
      tailf:info "Configure the rate at which traffic is sampled "+
        "and sent for Cflowd analysis";
      tailf:cli-no-value-on-delete;
      type uint16 {
        range "1..10000";
      }
    }
    // cflowd / template-retransmit
    leaf template-retransmit {
      tailf:info "Configure the time interval to resend template "+
        "information";
      tailf:cli-no-value-on-delete;
      type uint16 {
        range "1..600";
      }
    }
    // cflowd / shutdown
    leaf shutdown {
      tailf:info "Administratively enable/disable Cflowd sampling";
      type empty;
    }
  }


  /// ========================================================================
  /// ipsec /
  /// ========================================================================

  // ipsec /
  container ipsec {
    tailf:info "Configure IPsec Parameters";
    tailf:cli-add-mode;
    // ipsec / ike-policy *
    list ike-policy {
      tailf:info "Configure IPsec IKE Policy";
      tailf:cli-embed-no-on-delete;
      key "ike-policy-id";
      leaf ike-policy-id {
        type uint16 {
          range "1..2048";
        }
      }
      // ipsec / ike-policy * / create
      leaf create {
        mandatory true;
        type empty;
        tailf:cli-hide-in-submode;
        tailf:cli-no-name-on-delete;
      }
      // ipsec / ike-policy * / auth-algorithm
      leaf auth-algorithm {
        tailf:info "Configure Authentication Algorithm for this IKE policy";
        tailf:cli-no-value-on-delete;
        type enumeration {
          enum md5;
          enum sha1;
          enum sha256;
          enum sha384;
          enum sha512;
          enum aes-xcbc;
        }
      }
      // ipsec / ike-policy * / auth-method
      leaf auth-method {
        tailf:info "Configure authentication method for this IKE policy";
        tailf:cli-no-value-on-delete;
        type enumeration {
          enum psk;
          enum plain-psk-xauth;
          enum cert-auth;
          enum psk-radius;
          enum cert-radius;
          enum eap;
          enum auto-eap-radius;
          enum auto-eap;
        }
      }
      // ipsec / ike-policy * / auto-eap-method
      leaf auto-eap-method {
        tailf:info "Configure auto EAP method";
        tailf:cli-no-name-on-delete;
        tailf:cli-no-value-on-delete;
        type enumeration {
          enum psk;
          enum cert;
          enum psk-or-cert;
        }
      }
      // ipsec / ike-policy * / auto-eap-own-method
      leaf auto-eap-own-method {
        tailf:info "Configure auto EAP method for itself";
        tailf:cli-no-name-on-delete;
        tailf:cli-no-value-on-delete;
        type enumeration {
          enum psk;
          enum cert;
        }
      }
      // ipsec / ike-policy * / description
      leaf description {
        tailf:info "Configure description for this IKE policy";
        tailf:cli-no-value-on-delete;
        type string {
          length "1..80";
        }
      }
      // ipsec / ike-policy * / dh-group
      leaf dh-group {
        tailf:info "Configure dh-group for this IKE policy";
        tailf:cli-no-value-on-delete;
        type enumeration {
          enum "1";
          enum "2";
          enum "5";
          enum "14";
          enum "15";
        }
      }
      // ipsec / ike-policy * / dpd
      container dpd {
        presence present;
        tailf:info "Configure DPD Parameters";
        tailf:cli-compact-syntax;
        //leaf dummy{
        //  tailf:cli-drop-node-name;
        //  type empty;
        //}
        // ipsec / ike-policy * / dpd interval
        leaf interval {
          tailf:cli-no-name-on-delete;
          tailf:cli-no-value-on-delete;
          type uint16 {
            range "10..300";
          }
        }
        // ipsec / ike-policy * / max retries
        leaf max-retries {
          tailf:cli-no-name-on-delete;
          tailf:cli-no-value-on-delete;
          type uint8 {
            range "2..5";
          }
        }
        // ipsec / ike-policy * / reply-only
        leaf reply-only {
          tailf:cli-no-name-on-delete;
          tailf:cli-no-value-on-delete;
          type empty;
        }
      }
      // ipsec / ike-policy * / encryption-algorithm
      leaf encryption-algorithm {
        tailf:info "Configure Encryption Algorithm for this IKE policy";
        tailf:cli-no-value-on-delete;
        type enumeration {
          enum "des";
          enum "3des";
          enum "aes128";
          enum "aes192";
          enum "aes256";
        }
      }
      // ipsec / ike-policy * / ike-mode
      leaf ike-mode  {
        tailf:info "Configure IKE mode for this IKE policy";
        tailf:cli-no-value-on-delete;
        type enumeration {
          enum "main";
          enum "aggressive";
        }
      }
      // ipsec / ike-policy * / ike-version
      leaf ike-version {
        tailf:info "Configure version of IKE";
        tailf:cli-no-name-on-delete;
        tailf:cli-no-value-on-delete;
        type uint8 {
          range "1..2";
        }
      }
      // ipsec / ike-policy * / ipsec-lifetime
      leaf ipsec-lifetime {
        tailf:info "Configure Phase2 life time for this IKE policy";
        tailf:cli-no-value-on-delete;
        type uint32 {
          range "1200..172800";
        }
      }
      // ipsec / ike-policy * / isakmp-lifetime
      leaf isakmp-lifetime {
        tailf:info "Configure Phase2 life time for this IKE policy";
        tailf:cli-no-value-on-delete;
        type uint32 {
          range "1200..172800";
        }
      }
      // ipsec / ike-policy * / match-peer-id-to-cert
      leaf match-peer-id-to-cert {
        tailf:info "Enable/disable matching of peer identifier with "+
          "certificate";
        type empty;
      }
      // ipsec / ike-policy * / nat-traversal
      container nat-traversal {
        presence present;
        tailf:info "Configure NAT Traversal Parameters";
        tailf:cli-compact-syntax;
        //leaf dummy {
        //  tailf:cli-drop-node-name;
        //  type empty;
        //}
        // ipsec / ike-policy * / nat-traversal force
        leaf force {
          tailf:cli-no-name-on-delete;
          type empty;
        }
        // ipsec / ike-policy * / nat-traversal keep-alive-interval
        leaf keep-alive-interval {
          tailf:cli-no-name-on-delete;
          tailf:cli-no-value-on-delete;
          type uint16 {
            range "120..600";
          }
        }
        // ipsec / ike-policy * / nat-traversal force-keep-alive
        leaf force-keep-alive {
          tailf:cli-no-name-on-delete;
          type empty;
        }
      }
      // ipsec / ike-policy * / own-auth-method
      leaf own-auth-method {
        tailf:info "Configure authentication method for IKE policy itself";
        tailf:cli-no-value-on-delete;
        type enumeration {
          enum "psk";
          enum "cert";
          enum "eap-only";
        }
      }
      // ipsec / ike-policy * / pfs
      container pfs  {
        presence present;
        tailf:info "Configure PFS for this IKE policy";
        tailf:cli-compact-syntax;
        //leaf dummy {
        //  tailf:cli-drop-node-name;
        //  type empty;
        //}
        // ipsec / ike-policy * / pfs dh-group
        leaf dh-group {
          tailf:cli-no-value-on-delete;
          tailf:cli-no-name-on-delete;
          type enumeration {
            enum "1";
            enum "2";
            enum "5";
            enum "14";
            enum "15";
          }
        }
      }
    }
    // ipsec / ipsec-transform * /
    list ipsec-transform {
      tailf:info "Configure IPsec Transform";
      tailf:cli-embed-no-on-delete;
      key "transform-id";
      leaf transform-id {
        type uint16 {
          range "1..2048";
        }
      }
      // ipsec / ipsec-transform * / create
      leaf create {
        mandatory true;
        type empty;
        tailf:cli-hide-in-submode;
        tailf:cli-no-name-on-delete;
      }
      // ipsec / ipsec-transform * / esp-auth-algorithm
      leaf esp-auth-algorithm {
        tailf:info "Configure Authentication Algorithm for this transform";
        tailf:cli-no-value-on-delete;
        type enumeration {
          enum "null";
          enum "md5";
          enum "sha1";
          enum "sha256";
          enum "sha384";
          enum "sha512";
          enum "aes-xcbc";
        }
      }
      // ipsec / ipsec-transform * / esp-encryption-algorithm
      leaf esp-encryption-algorithm {
        tailf:info "Configure Encryption Algorithm for this transform";
        tailf:cli-no-value-on-delete;
        type enumeration {
          enum "null";
          enum "des";
          enum "3des";
          enum "aes128";
          enum "aes192";
          enum "aes256";
        }
      }
    }
  }

  /// ========================================================================
  /// isa /
  /// ========================================================================
  container isa {
    tailf:info "Configure Integrated Services Adaptors";
    tailf:cli-recursive-delete;
    tailf:cli-embed-no-on-delete;
    // isa / tunnel-group * /
    list tunnel-group {
      tailf:info "Configure an ISA Tunnel Group";
      key tunnel-group-id;
      leaf tunnel-group-id {
        tailf:cli-drop-node-name;
        type uint16 {
          range "1..16";
        }
      }
      // isa / tunnel-group * / primary
      leaf primary {
        // Todo: the mda-id has the format <slot>/<mda>
        tailf:info "Configure ISA-Tunnel-Group primary ISA";
        type string;
      }
        // isa / tunnel-group * / shutdown
      leaf shutdown {
        tailf:info "Administratively enable/disable an ISA-Tunnel-Group";
        tailf:cli-boolean-no;
        default true;
        type boolean;
      }
    }
  }

  /// ========================================================================
  /// lag *
  /// ========================================================================
  list lag {
    tailf:info "Create/delete context for configuring LAG attributes";
    tailf:cli-embed-no-on-delete;
    tailf:cli-recursive-delete;
    tailf:cli-diff-dependency "/alu:port";
    key id;
    leaf id {
      type uint32;
    }

    // lag * / description
    leaf description {
      tailf:cli-no-value-on-delete;
      type string;
    }

    // lag * / mode
    leaf mode {
      tailf:info "<mode>;;access|network|hybrid";
      tailf:cli-no-value-on-delete;
      type enumeration {
        enum access;
        enum network;
        enum hybrid;
      }
    }

    // lag * / encap-type
    leaf encap-type {
      tailf:info "Encapsulation type";
      tailf:cli-no-value-on-delete;
      type enumeration {
        enum dot1q;
        enum null;
        enum qinq;
      }
    }

    // lag * / port *
    list port {
      tailf:cli-suppress-mode;
      key id;
      leaf id {
        tailf:non-strict-leafref {
          path "/alu:port/port-id";
        }
        type string;
      }

      // lag * / port * / priority
      leaf priority {
        type uint32;
      }
    }

    // lag * / port-threshold
    container port-threshold {
      tailf:cli-embed-no-on-delete;
      tailf:cli-compact-syntax;
      tailf:cli-sequence-commands;

      // lag * / port-threshold value
      leaf value {
        tailf:cli-drop-node-name;
        tailf:cli-no-value-on-delete;
        type uint8 {
          range "0..31";
        }
      }

      // lag * / port-threshold action
      leaf action {
        type enumeration {
          enum dynamic-cost;
          enum down;
        }
      }
    }

    // lag * / lacp
    container lacp {
      tailf:cli-embed-no-on-delete;
      tailf:cli-compact-syntax;
      tailf:cli-sequence-commands;

      // lag * / lacp mode
      leaf mode {
        tailf:cli-drop-node-name;
        tailf:cli-no-value-on-delete;
        type enumeration {
          enum passive;
          enum active;
        }
      }

      // lag * / lacp administrative-key
      leaf administrative-key {
        tailf:cli-no-value-on-delete;
        tailf:cli-no-name-on-delete;
        tailf:cli-optional-in-sequence;
        type uint16;
      }

      // lag * / lacp system-id
      leaf system-id {
        tailf:cli-no-value-on-delete;
        tailf:cli-no-name-on-delete;
        tailf:cli-optional-in-sequence;
        type string;
      }

      // lag * / lacp system-priority
      leaf system-priority {
        tailf:cli-no-value-on-delete;
        tailf:cli-no-name-on-delete;
        type uint16;
      }
    }

    // lag * / shutdown
    leaf shutdown {
      tailf:cli-boolean-no;
      default true;
      type boolean;
    }
  }

  /// ========================================================================
  /// port /
  /// ========================================================================
  list port {
    tailf:info "Configure physical ports";
    tailf:cli-recursive-delete;
    tailf:cli-embed-no-on-delete;
    key port-id;
    leaf port-id {
      type string;
    }

    leaf description {
      tailf:cli-no-value-on-delete;
      type string;
    }

    // port * / ethernet /
    container ethernet {
      tailf:info "Configure attributes for an ethernet port";
      tailf:cli-add-mode;

      // port * / ethernet / mode
      leaf mode {
        tailf:info "Configure an ethernet port for access or network mode";
        tailf:cli-no-value-on-delete;
        tailf:cli-diff-dependency "../network" {
          tailf:cli-trigger-on-all;
        }
        tailf:cli-diff-dependency "../access" {
          tailf:cli-trigger-on-all;
        }
        type enumeration {
          enum access;
          enum network;
          enum hybrid;
        }
      }

      // port * / ethernet / access
      container access {
        tailf:info "Configure ethernet access port parameters";
        tailf:cli-add-mode;
        tailf:cli-diff-dependency "../mode";

        leaf accounting-policy {
          tailf:info "Configure the accounting policy which applies to the"
            + " access port";
          tailf:cli-embed-no-on-delete;
          tailf:cli-no-value-on-delete;
          type uint8 {
            range "0..99";
          }
        }

        leaf collect-stats {
          tailf:info "Enable/disable the collection of statistical data";
          tailf:cli-embed-no-on-delete;
          type empty;
        }

        container egress {
          tailf:info "Configure ethernet access egress port parameters";
          tailf:cli-add-mode;

          leaf qos {
            tailf:cli-embed-no-on-delete;
            type uint16 {
              range "1..65535";
            }
          }
        }
      }

      // port * / ethernet / autonegiotiate
      container autonegotiate {
        tailf:info "Enable/disable speed and duplex autonegotiation on"
                 + " an ethernet port";
        tailf:cli-embed-no-on-delete;
        presence true;
        leaf limited {
          tailf:cli-no-name-on-delete;
          type empty;
        }
      }

      // port * / ethernet / dot1q-etype
      leaf dot1q-etype {
        tailf:info "Configure the ethertype used for dot1q encapsulation";
        tailf:cli-no-value-on-delete;
        type uint32 {
          range "1536..65535";
        }
      }

      // port * / ethernet / duplex
      leaf duplex {
        tailf:info "Configure duplex of an ethernet port";
        tailf:cli-no-value-on-delete;
        type enumeration {
          enum full;
          enum half;
        }
      }

      // port * / ethernet / efm-oam
      container efm-oam {
        tailf:info "Configure EFM-OAM attributes";
        tailf:cli-add-mode;
        leaf accept-remote-loopback {
          type empty;
        }
        container transmit-interval {
          tailf:cli-compact-syntax;
          tailf:cli-sequence-commands;
          leaf interval {
            tailf:cli-drop-node-name;
            type uint16 {
              range "1..600";
            }
          }
          leaf multiplier {
            type uint8 {
              range "2..5";
            }
          }
        }
      }


      // port * / ethernet / encap-type
      leaf encap-type {
        tailf:info "Configure encapsulation method";
        tailf:cli-no-value-on-delete;
        type enumeration {
          enum dot1q;
          enum null;
          enum qinq;
        }
      }

      // port * / ethernet / egress-rate
      leaf egress-rate {
        tailf:info "Specify the egress-rate";
        tailf:cli-no-value-on-delete;
        type uint32 {
          range "1..10000000";
        }
      }

      // port * / ethernet / egress-scheduler-policy
      leaf egress-scheduler-policy {
        tailf:info "Configure an egress scheduler policy";
        tailf:cli-no-value-on-delete;
        tailf:cli-embed-no-on-delete;
        tailf:cli-diff-dependency "/alu:qos/port-scheduler-policy";
        tailf:non-strict-leafref {
          path "/alu:qos/port-scheduler-policy/name";
        }
        type string;
      }

      // port * / ethernet / egress-scheduler-override
      container egress-scheduler-override {
        tailf:info "Apply egress scheduler overrides";
        tailf:cli-embed-no-on-delete;
        tailf:cli-diff-dependency "../egress-scheduler-policy";
        tailf:cli-add-mode;

        // port * / ethernet / egress-scheduler-override level *
        list level {
          tailf:info "Configure priority level parameters";
          tailf:cli-suppress-mode;
          tailf:cli-compact-syntax;
          tailf:cli-sequence-commands;
          key priority-level;
          leaf priority-level {
            type uint8 {
              range "1..8";
            }
          }

          leaf rate {
            tailf:cli-no-value-on-delete;
            tailf:cli-no-name-on-delete;
            type union {
              type uint32 {
                range "1..40000000";
              }
              type enumeration {
                enum max;
              }
            }
          }

          leaf cir {
            tailf:cli-no-value-on-delete;
            tailf:cli-no-name-on-delete;
            type union {
              type uint32 {
                range "0..40000000";
              }
              type enumeration {
                enum max;
              }
            }
          }
        }

        // port * / ethernet / egress-scheduler-override * max-rate
        leaf max-rate {
          tailf:cli-no-value-on-delete;
          type union {
            type uint32 {
              range "1..40000000";
            }
            type enumeration {
              enum max;
            }
          }
        }
      }

      // port / ethernet / hold-time
      container hold-time {
        tailf:info "Configure port link dampening timers";
        tailf:cli-embed-no-on-delete;
        tailf:cli-compact-syntax;
        tailf:cli-sequence-commands;

        // port / ethernet / hold-time up
        leaf up {
          tailf:cli-no-name-on-delete;
          tailf:cli-no-value-on-delete;
          type uint32 {
            range "0..90000";
          }
        }

        // port / ethernet / hold-time down
        leaf down {
          tailf:cli-no-name-on-delete;
          tailf:cli-no-value-on-delete;
          type uint32 {
            range "0..90000";
          }
        }

        // port / ethernet / hold-time unit
        leaf unit {
          tailf:cli-drop-node-name;
          tailf:cli-no-value-on-delete;
          type enumeration {
            enum seconds;
            enum centiseconds;
          }
        }
      }

      // port * / ethernet / inress-rate
      leaf ingress-rate {
        tailf:info "Configure the maximum amount of ingress bandwidth that "+
          "this port can receive";
        tailf:cli-no-value-on-delete;
        type uint32 {
          range "1..100000";
        }
      }

      // port * / ethernet / lldp
      container lldp {
        tailf:info "Configure Link Layer Discovery Protocol parameters";
        tailf:cli-add-mode;

        // port * / ethernet / lldp / dest-mac *
        list dest-mac {
          tailf:info "Configure the destination mac-address parameters";
          max-elements 3;
          key id;
          leaf id {
            type enumeration {
              enum nearest-bridge;
              enum nearest-non-tpmr;
              enum nearest-customer;
            }
          }

          leaf notification {
            tailf:info "Enable/Disable LLDP notifications";
            tailf:cli-embed-no-on-delete;
            type empty;
          }

          leaf admin-status {
            tailf:info "Configure LLDP transmission/reception frame handling";
            type enumeration {
              enum "rx";
              enum "tx";
              enum "tx-rx";
              enum "disabled";
            }
          }
          // port * / ethernet / lldp / dest-mac * / tx-tlvs
          container tx-tlvs {
            tailf:info "Configure the LLDP TLVs to transmit";
            tailf:cli-compact-syntax;
            leaf port-desc {
              type empty;
            }

            leaf sys-name {
              type empty;
            }

            leaf sys-desc {
              type empty;
            }

            leaf sys-cap {
              type empty;
            }
          }
          // port * / ethernet / lldp / dest-mac * / tx-mgmt-address
          leaf tx-mgmt-address {
            tailf:info "Configure which management address to transmit";
            type enumeration {
              enum "system";
            }
          }
        }
      }

      // port * / ethernet / mac
      leaf mac {
        tailf:info "Assign a specific MAC address to an ethernet port";
        tailf:cli-no-value-on-delete;
        type ieee-mac;
      }

      // port * / ethernet / mtu
      leaf mtu {
        tailf:info "Configure the maximum payload MTU for an ethernet port";
        tailf:cli-no-value-on-delete;
        type uint16;
      }

      // port * / ethernet / network
      container network {
        tailf:info "Configure network port parameters";
        tailf:cli-diff-dependency "../mode" {
          tailf:cli-trigger-on-set;
        }
        tailf:cli-recursive-delete;
        tailf:cli-add-mode;

        // port * / ethernet / network / queue-policy
        leaf queue-policy {
          tailf:info "Configure the network policy";
          tailf:cli-no-value-on-delete;
          tailf:non-strict-leafref {
            path "/alu:qos/network-queue/network-queue-name";
          }
          type string;
        }

        // port * / ethernet / network / scheduler-mode
        leaf scheduler-mode {
          tailf:info "Configure egress scheduler mode";
          tailf:cli-no-value-on-delete;
          tailf:cli-no-name-on-delete;
          type enumeration {
            enum profile;
            enum 4-priority;
            enum 16-priority;
          }
        }
      }
    }

    // port * / dwdm /
    container dwdm {
      tailf:info "Configure the Dense Wavelength Division "
              + "Multiplexing parameters";
      tailf:cli-add-mode;

      // port * / dwdm / amplifier
      container amplifier {
        tailf:info "Configure the optical port amplifier parameters";
        tailf:cli-add-mode;

         // port * / dwdm / amplifier / report-alarms
        leaf-list report-alarms {
          tailf:info "Enable/disable logging of optical amplifier "
                      + "alarms on port";
          type enumeration {
            enum ild;
            enum tmp;
            enum mth;
            enum mtl;
            enum los;
            enum lop;
            enum com;
          }
        }
      }

      // port * / dwdm / channel
      leaf channel {
        tailf:info "Configure the DWDM channel number";
        type uint16 {
          range "0 | 17..61| 175..605";
          tailf:info "<dwdm channel>;;[0|17-61|175-605]";
        }
      }

      // port * / dwdm / coherent
      container coherent {
        tailf:cli-add-mode;
        leaf target-power {
          type decimal64 {
            range "-20..3";
            fraction-digits 3;
            tailf:info "<dwdm target power in dBM>[-20.00..3.00]";
          }
        }
        // port * / dwdm / coherent / compatibility
        leaf compatibility {
          type enumeration {
            enum interop;
            enum interop2;
          }
        }
        // port * / dwdm / coherent / sweep
        container sweep {
          tailf:cli-compact-syntax;
          leaf start {
            type int32;
          }
          leaf end {
            type int32;
          }
        }

        // port * / dwdm / coherent / channel
        leaf channel {
          type uint16 {
            range "0 | 17..61| 175..605";
            tailf:info "<dwdm channel>;;[0|17-61|175-605]";
          }
        }
        // port * / dwdm / coherent / mode
        leaf mode {
          type enumeration {
            enum manual;
          }
        }
      }

      // port * / dwdm / rxdtv-adjust
      leaf rxdtv-adjust {
        tailf:info "Enable/Disable Rx Decision Threshold Voltage "
          + "Adjustment feedback.";
        type empty;
      }

      // port * / dwdm / tdcm /
      container tdcm {
        tailf:info "Configure the Tunable Dispersion "
                  +"Compensation Module parameters";
        tailf:cli-add-mode;

        // port * / dwdm / tdcm / channel
        leaf channel {
          tailf:info "Configure the tdcm received channel number";
          type uint16 {
            range "0 | 17..61| 175..605";
          }
        }

        // port * / dwdm / tdcm / dispersion
        leaf dispersion {
          tailf:info "Configure the dispersion compensation (ps/nm)";
          type int32 {
            range "-1200..1200";
          }
        }

        // port * / dwdm / tdcm / mode
        leaf mode {
          tailf:info "Configure the dispersion algorithm mode used";
          type enumeration {
            enum automatic;
            enum manual;
          }
        }

        // port * / dwdm / tdcm / report-alarms
         leaf-list report-alarms {
           tailf:info "Enable/disable logging of tdcm alarms on port";
           type enumeration {
            enum ild;
            enum tmp;
            enum mth;
            enum mtl;
            enum los;
            enum lop;
            enum com;
          }
         }

        // port * / dwdm / tdcm / sweep
        container sweep {
          tailf:info "Configure the dispersion sweep start and end "
                  +"values for the link (ps/nm)";
          tailf:cli-compact-syntax;
          tailf:cli-sequence-commands;

          leaf start {
            type int32 {
              range "-1200..1200";
            }
          }

          leaf end {
            type int32 {
              range "-1200..1200";
            }
          }
        }

        leaf shutdown {
          tailf:info "Administratively enable/disable the channel";
          tailf:cli-boolean-no;
          default true;
          type boolean;
        }
      }
    }

    // port * / modify-buffer-allocation-rate /
    container modify-buffer-allocation-rate {
      tailf:info "Configure modify buffer allocation rate";
      tailf:cli-add-mode;
      // port * / modify-buffer-allocation-rate / egr-percentage-of-rate
      leaf egr-percentage-of-rate {
        tailf:cli-no-value-on-delete;
        tailf:info "Configure egress percentage of rate";
        type uint16 {
          range "1..1000";
        }
      }
      leaf ing-percentage-of-rate {
        tailf:cli-no-value-on-delete;
        tailf:info "Configure ingress percentage of rate";
        type uint16 {
          range "1..1000";
        }
      }
    }

    // port * / multilink-bundle
    container multilink-bundle {
      tailf:cli-add-mode;
      // port * / multilink-bundle / fragmented-threshold
      leaf fragment-threshold {
        tailf:info "Configure the maximum bytes of a fragment transmitted";
        tailf:cli-no-value-on-delete;
        type union {
          type uint16 {
            range "128..512";
          }
          type enumeration {
            enum unlimited;
          }
        }
      }
      // port * / multilink-bundle / member *
      list member {
        tailf:info "Add a member port to the bundle";
        tailf:cli-embed-no-on-delete;
        tailf:cli-suppress-mode;
        key id;

        leaf id {
          type string;
        }
      }
    }

    // port * / network /
    container network {
      tailf:info "Configure the network parameters for a port";
      tailf:cli-recursive-delete;
      tailf:cli-add-mode;
      // port * / network / egress
      container egress {
        tailf:info "Configure network egress port parameters";
        tailf:cli-add-mode;
        // port * / network / egress / pool
        container pool {
          tailf:info "Configure the egress pool policy for the port";
          tailf:cli-add-mode;
          // port * / network / egress / slope-policy
          leaf slope-policy {
            tailf:info "Configure the slope policy";
            tailf:cli-no-value-on-delete;
            type string {
              length "1..32";
            }
          }
        }
      }
    }
    // port * / otu
    container otu {
      tailf:info "Configure Optical Transport Unit (OTU) parameters";
      tailf:cli-embed-no-on-delete;
      tailf:cli-add-mode;

      // port * / otu / async-mapping
      leaf async-mapping {
        tailf:info "Enable/Disable OTU asynchronous mapping; "
                  + "synchronous when disabled";
        type empty;
      }

      // port * / otu / fec
      leaf fec {
        tailf:info "Configure the Forwarding Error Correction (FEC) params";
        tailf:cli-no-value-on-delete;
        type enumeration {
          enum g709;
          enum enhanced;
        }
      }

      // port * / otu / otu2-lan-data-rate
      leaf otu2-lan-data-rate {
        tailf:info "Configure the 10GE LAN OTU2 Data Rate";
        type enumeration {
          enum "11.049";
          enum "11.096";
        }
      }

      // port * / otu / report-alarms
      leaf-list report-alarms {
        tailf:info "Enable/Disable the OTU alarms";
        type enumeration {
          enum loc;
          enum los;
          enum lof;
          enum lom;
          enum otu-ais;
          enum otu-ber-sf;
          enum otu-ber-sd;
          enum otu-bdi;
          enum otu-tim;
          enum otu-iae;
          enum otu-biae;
          enum fec-sf;
          enum fec-sd;
          enum fec-fail;
          enum fec-uncorr;
          enum odu-ais;
          enum odu-oci;
          enum odu-lck;
          enum odu-bdi;
          enum odu-tim;
          enum opu-tim;
          enum opu-plm;
        }
      }
      // port * / otu / sd-threshold
      leaf sd-threshold {
        tailf:info "Configure the Signal Degrade (SD) threshold";
        type uint8 {
          range "5..9";
        }
      }

      // port * / otu / sf-sd-method
      leaf sf-sd-method {
        tailf:info "Configure the Signal Fail/Degrade method for the port";
        type enumeration {
          enum bip8;
          enum fec;
        }
      }

      // port * / otu / sf-threshold
      leaf sf-threshold {
        tailf:info "Configure the Signal Fail (SF) threshold";
        type uint8 {
          range "3..6";
        }
      }
    }

    container sonet-sdh {
      tailf:cli-add-mode;

      leaf clock-source {
        tailf:info "Configure the clock for transmitted data";
        tailf:cli-no-value-on-delete;
        type enumeration {
          enum loop-timed;
          enum node-timed;
        }
      }

      leaf framing {
        tailf:info "Configure SONET/SDH framing";
        tailf:cli-no-value-on-delete;
        type enumeration {
          enum sonet;
          enum sdh;
        }
      }

      container group {
        tailf:info "Configure the payload of the SONET/SDH group";
        tailf:cli-embed-no-on-delete;
        tailf:cli-compact-syntax;
        tailf:cli-sequence-commands;

        leaf sonet-sdh-index {
          tailf:cli-drop-node-name;
          tailf:cli-no-value-on-delete;
          type uint32;
        }

        leaf payload {
          tailf:cli-no-value-on-delete;
          type enumeration {
            enum tu3;
            enum vt2;
            enum vt15;
          }
        }
      }

      container hold-time {
        tailf:info "Configure SONET link dampening timers in 100s of ms";
        tailf:cli-embed-no-on-delete;
        tailf:cli-compact-syntax;

        leaf up {
          tailf:cli-no-value-on-delete;
          tailf:cli-no-name-on-delete;
          type uint8 {
            range "0..100";
          }
        }

        leaf down {
          tailf:cli-no-value-on-delete;
          tailf:cli-no-name-on-delete;
          type uint8 {
            range "0..100";
          }
        }
      }

      leaf loopback {
        tailf:info "Activate a loopback on the SONET port";
        tailf:cli-no-value-on-delete;
        type enumeration {
          enum line;
          enum internal;
        }
      }

      list path {
        tailf:info "Configure SONET/SDH path properties";
        tailf:cli-embed-no-on-delete;
        key sonet-sdh-index;

        leaf sonet-sdh-index {
          tailf:info "sts12/sts3/tu3/vt2/vt15/sts1 sonet-sdh index";
          type string;
        }

        leaf payload {
          tailf:info "Configure the SONET/SDH path payload";
          type enumeration {
            enum sts3;
            enum tug3;
            enum ds3;
            enum e3;
            enum vt2;
            enum vt15;
            enum ds1;
            enum e1;
          }
        }
      }

      leaf report-alarm {
        tailf:info "Enable/disable logging of line and section alarms for "
          + "a port";
        type enumeration {
          enum lais;
          enum lrdi;
          enum ss1f;
          enum lb2er-sd;
          enum lb2er-sf;
          enum slof;
          enum slos;
          enum lrei;
          enum loc;
        }
      }

      container section-trace {
        tailf:info "Configure section trace bytes in the SONET section header";

        choice a {
          leaf increment-z0 {
            type empty;
          }

          leaf byte {
            type uint8;
          }

          leaf string {
            type string {
              length "1..16";
            }
          }
        }
      }

      leaf single-fiber {
        tailf:info "Enable/disable single fiber";
        type empty;
      }

      leaf speed {
        tailf:info "Configure the speed of a port to be either OC3 or OC12";
        tailf:cli-no-value-on-delete;
        type enumeration {
          enum oc3;
          enum oc8;
        }
      }

      leaf suppress-lo-alarm {
        tailf:info "Suppress lo order alarms";
        type empty;
      }

      container  threshold {
        tailf:info "Configure the line signal degradation BER thresholds";
        tailf:cli-compact-syntax;
        tailf:cli-sequence-commands;
        tailf:cli-embed-no-on-delete;

        leaf value {
          tailf:cli-drop-node-name;
          tailf:cli-no-value-on-delete;
          type enumeration {
            enum ber-sd;
            enum ber-sf;
          }
        }

        leaf rate {
          tailf:cli-no-value-on-delete;
          type uint8 {
            range "3..9";
          }
        }
      }

      leaf tx-dus {
        tailf:info "Enable/disable the forced transmit in S1 overhead byte";
        type empty;
      }
    }
    // port * / tdm
    container tdm {
      tailf:info "Configure attributes for a TDM port";
      tailf:cli-add-mode;

      leaf buildout {
        tailf:info "Configure the line buildout for the physical DS1/DS3";
        type enumeration {
          enum long;
          enum short;
        }
      }

      // port * / tdm / ds1 *
      list ds1 {
        tailf:info "Configure DS1 channel parameters";
        tailf:cli-embed-no-on-delete;
        key ds1-id;

        leaf ds1-id {
          tailf:info "ds1-number(1-28)|ds1-sonet-sdh-index";
          type string;
        }

        container bert  {
          tailf:info "Start/Stop a Bit Error Rate Test (BERT)";
          tailf:cli-embed-no-on-delete;
          tailf:cli-compact-syntax;
          tailf:cli-sequence-commands;

          leaf value {
            tailf:cli-no-value-on-delete;
            type enumeration {
              enum 2e3;
              enum 2e9;
              enum 2e11;
              enum 2e15;
              enum 2e20;
              enum 2e20q;
              enum 2e23;
              enum ones;
              enum zeros;
              enum alternating;
            }
          }

          leaf duration {
            tailf:info "sec|hh:mm[:sec] 24 hour max";
            tailf:cli-no-value-on-delete;
            type string;
          }
          }


        leaf bit-error-insertion {
          tailf:info "Configure the bit error insert rate for the BERT test";
          tailf:cli-no-value-on-delete;
          type uint8 {
            range "2..7";
          }
        }

        list channel-group {
          tailf:info "Create/delete DS0 channel groups";
          tailf:cli-embed-no-on-delete;
          max-elements 24;
          key id;

          leaf id {
            type uint8 {
              range "1..24";
            }
          }

          // port * / tdm / ds1 * / clock-source
          leaf clock-source {
            tailf:info "Configure the clock for transmitted data";
            tailf:cli-no-name-on-delete;
            tailf:cli-no-value-on-delete;
            type enumeration {
              enum "loop-timed";
              enum "node-timed";
            }
          }

          leaf encap-type {
            tailf:info "Configure an encap method";
            tailf:cli-no-value-on-delete;
            type enumeration {
              enum atm;
              enum bcp-null;
              enum bcp-dot1q;
              enum ipcp;
              enum ppp-auto;
              enum frame-relay;
              enum wan-mirror;
              enum cisco-hdlc;
              enum cem;
            }
          }

          container ppp {
            tailf:info "Configure the LCP operational parameters";
            tailf:cli-add-mode;

            leaf ber-sf-link-down {
              tailf:info "Enable/Disable port down on BER-SF alarm";
              type empty;
            }
          }

          leaf timeslots {
            tailf:info "timeslot range [1..24] (e.g. 1-10,21,23)";
            tailf:cli-no-value-on-delete;
            type string;
          }

          leaf shutdown {
            tailf:cli-boolean-no;
            default true;
            type boolean;
          }
        }

        leaf clock-source {
          tailf:info "Configure the clock for transmitted data";
          tailf:cli-no-value-on-delete;
          type enumeration {
            enum loop-timed;
            enum node-timed;
            enum adaptive;
            enum differential;
          }
        }

        leaf framing {
          tailf:info "Configure the framing for the channel";
          tailf:cli-no-value-on-delete;
          type enumeration {
            enum esf;
            enum sf;
            enum ds1-unframed;
          }
        }

        leaf invert-data {
          tailf:info "Enable/disable inverting of data bits";
          type empty;
        }

        leaf loopback {
          tailf:info "Activate a loopback on the channel";
          tailf:cli-no-value-on-delete;
          type enumeration {
            enum line;
            enum internal;
            enum fdl-ansi;
            enum fdl-bellcore;
            enum payload-ansi;
            enum inband-ansi;
            enum inband-bellcore;
          }
        }

        leaf remote-loop-respond {
          tailf:info "Enable/disable response to remote loop";
          type empty;
        }

        leaf report-alarm {
          tailf:info "Enable/disable logging of alarms";
          tailf:cli-no-value-on-delete;
          type enumeration {
            enum ais;
            enum los;
            enum oof;
            enum rai;
            enum looped;
            enum ber-sd;
            enum ber-sf;
          }
        }

        leaf signal-mode {
          tailf:info "Activate the signal-mode on the channel";
          tailf:cli-no-value-on-delete;
          type enumeration {
            enum cas;
          }
        }

        container threshold {
          tailf:info "Configure BER signal degradation failure thresholds";
          tailf:cli-embed-no-on-delete;
          tailf:cli-compact-syntax;
          tailf:cli-sequence-commands;

          leaf value {
            tailf:cli-no-value-on-delete;
            type enumeration {
              enum ber-sd;
              enum ber-sf;
            }
          }

          leaf rate {
            tailf:info "Number of errors in millions";
            tailf:cli-no-value-on-delete;
            type enumeration {
              enum 1;
              enum 5;
              enum 10;
              enum 50;
              enum 100;
            }
          }
        }

        leaf shutdown {
          tailf:info "Administratively enable/disable the channel";
          tailf:cli-boolean-no;
          default true;
          type boolean;
        }
      }

      // port * / tdm / ds3 *
      list ds3 {
        tailf:info "Configure DS3 channel parameters";
        tailf:cli-embed-no-on-delete;
        key ds3-id;

        leaf ds3-id {
          tailf:info "ds1-number(1-28)|ds1-sonet-sdh-index";
          type string;
        }
        // port * / tdm / ds3 * / bert
        container bert  {
          tailf:info "Start/Stop a Bit Error Rate Test (BERT)";
          tailf:cli-embed-no-on-delete;
          tailf:cli-compact-syntax;
          tailf:cli-sequence-commands;

          leaf value {
            tailf:cli-no-value-on-delete;
            type enumeration {
              enum 2e3;
              enum 2e9;
              enum 2e11;
              enum 2e15;
              enum 2e20;
              enum 2e20q;
              enum 2e23;
              enum ones;
              enum zeros;
              enum alternating;
            }
          }
        }

        // port * / tdm / ds3 * / channelized
        leaf channelized {
          tailf:info "Specify if the DS3 port is channelized";
          tailf:cli-no-value-on-delete;
          type enumeration {
            enum ds1;
            enum e1;
          }
        }
        // port * / tdm / ds3 * / clock-source
        leaf clock-source {
          tailf:info "Configure the clock for transmitted data";
          tailf:cli-no-name-on-delete;
          tailf:cli-no-value-on-delete;
          type enumeration {
            enum "loop-timed";
            enum "node-timed";
          }
        }
        // port * / tdm / ds3 * / encap-type
        leaf encap-type {
          tailf:info "Configure an encap method";
          tailf:cli-no-value-on-delete;
          type enumeration {
            enum atm;
            enum bcp-null;
            enum bcp-dot1q;
            enum ipcp;
            enum ppp-auto;
            enum frame-relay;
            enum wan-mirror;
            enum cisco-hdlc;
            enum cem;
          }
        }

        // port * / tdm / ds3 * / shutdown
        leaf shutdown {
          tailf:info "Administratively enable/disable the port";
          tailf:cli-boolean-no;
          default true;
          type boolean;
        }
      }

      leaf lbo {
        tailf:info "Configure the transmitter attenuation for a long buildout";
        tailf:cli-no-value-on-delete;
        type enumeration {
          enum "0dB";
          enum "-7.5dB";
          enum "-15.0dB";
          enum "-22.5dB";
        }
      }

      leaf length {
        tailf:info "Configure the cable length for a short buildout";
        tailf:cli-no-value-on-delete;
        type enumeration {
          enum 133;
          enum 266;
          enum 399;
          enum 533;
          enum 655;
        }
      }
    }

    // port * / shutdown
     leaf shutdown {
      tailf:cli-boolean-no;
      default true;
      type boolean;
    }
  }

  /// ========================================================================
  /// qos /
  /// ========================================================================
  container qos {
    tailf:info "Configure QoS policies";
    tailf:cli-add-mode;
    // qos / fabric-profile
    list fabric-profile {
      // This list is on 7705 only. Should be conditioned.
      tailf:info "Configure fabric-profile policy";
      tailf:cli-recursive-delete;
      tailf:cli-embed-no-on-delete;
      key policy-id;
      leaf policy-id {
        type uint16 {
          range "1..256";
        }
      }
      // qos / fabric-profile * mode
      leaf mode {
        tailf:info "Specify mode of profile";
        tailf:cli-drop-node-name;
        tailf:cli-no-value-on-delete;
        tailf:cli-hide-in-submode;
        type enumeration {
          enum aggregate-mode;
          enum destination-mode;
        }
      }
      // qos / fabric-profile * / aggregate-rate
      leaf aggregate-rate {
        tailf:info "Configure rate in aggregate mode";
        tailf:cli-no-value-on-delete;
        type union {
          type enumeration {
            enum default;
          }
          type uint32 {
            range "1..10000000";
          }
        }
      }
      // qos / fabric-profile * / description
      leaf description {
        tailf:info "Description for this policy";
        tailf:cli-no-value-on-delete;
        type string;
      }
      // qos / fabric-profile * / dest-mda
      list dest-mda {
        tailf:info "Configure a destination mda shaping policy";
        key id;
        leaf id {
          type union {
            type enumeration {
              enum multipoint;
            }
            type uint32;
          }
        }
        // qos / fabric-profile * / dest-mda * / rate
        leaf rate {
          tailf:info "Specify rate to destination MDA";
          type union {
            type enumeration {
              enum default;
            }
            type uint32 {
              range "1..10000000";
            }
          }
        }
      }

      leaf create {
        tailf:cli-hide-in-submode;
        tailf:cli-no-name-on-delete;
        mandatory true;
        type empty;
      }
    }

    // qos / network-queue *
    list network-queue {
      //tailf:cli-recursive-delete;
      tailf:cli-embed-no-on-delete;
      tailf:callpoint network-queue-hook { tailf:set-hook node; }
      key network-queue-name;
      leaf network-queue-name {
        type string;
      }

      leaf create {
        tailf:cli-hide-in-submode;
        tailf:cli-no-name-on-delete;
        mandatory true;
        type empty;
      }

      leaf description {
        tailf:cli-embed-no-on-delete;
        tailf:cli-no-value-on-delete;
        type string;
      }

      // qos / network-queue * / queue *
      list queue {
        key id;

        leaf id {
          type uint32;
        }

        leaf multipoint {
          tailf:cli-hide-in-submode;
          tailf:cli-no-name-on-delete;
          type empty;
        }

        leaf queue-type {
          tailf:cli-drop-node-name;
          tailf:cli-hide-in-submode;
          tailf:cli-no-value-on-delete;
          type enumeration {
            enum expedite;
            enum best-effort;
            enum auto-expedite;
          }
        }

        leaf create {
          mandatory true;
          type empty;
          tailf:cli-hide-in-submode;
          tailf:cli-no-name-on-delete;
        }

        leaf mbs {
          tailf:info "Specify MBS";
          default 50;
          type decimal64 {
            fraction-digits 2;
            range "0..100";
          }
        }

        leaf cbs {
          tailf:info "Specify CBS";
          type decimal64 {
            fraction-digits 2;
            range "0..100";
          }
        }

        leaf high-prio-only {
          tailf:info "Specify high priority only burst size";
          default 10;
          type union {
            type enumeration {
              enum default;
            }
            type uint8;
          }
        }

        container rate {
          tailf:info "Specify rates (CIR and PIR)";
          tailf:cli-compact-syntax;
          tailf:cli-sequence-commands;
          leaf percent {
            tailf:cli-drop-node-name;
            type uint8 {
              range "0..100";
            }
          }
          leaf cir {
            type uint8 {
              range "0..100";
            }
          }
        }

        // qos / network-queue * / queue * / port-parent
        container port-parent {
          presence present;
          tailf:info "Specify the port-scheduler to which this queue feeds";
          tailf:cli-compact-syntax;
          tailf:cli-embed-no-on-delete;
          leaf weight {
            tailf:cli-no-name-on-delete;
            tailf:cli-no-value-on-delete;
            type uint8 {
              range "0..100";
            }
          }
          leaf level {
            tailf:cli-no-name-on-delete;
            tailf:cli-no-value-on-delete;
            type uint8 {
              range "1..8";
            }
          }
          leaf cir-weight {
            tailf:cli-no-name-on-delete;
            tailf:cli-no-value-on-delete;
            type uint8 {
              range "0..100";
            }
          }
          leaf cir-level {
            tailf:cli-no-name-on-delete;
            tailf:cli-no-value-on-delete;
            type uint8 {
              range "0..8";
            }
          }
        }
      }
      // qos / network-queue * /
      list fc {
        key id;

        leaf id {
          type string;
        }

        leaf create {
          mandatory true;
          type empty;
          tailf:cli-hide-in-submode;
          tailf:cli-no-name-on-delete;
        }

        leaf multicast-queue {
          type uint8;
        }

        leaf queue {
          type uint8;
        }

        container egress-hsmda {
          tailf:cli-add-mode;

          leaf queue {
            type uint8;
          }
        }
      }
    }

    // qos / queue-group-templates /
    container queue-group-templates {
      tailf:info "Configure QoS queue groups";
      tailf:cli-add-mode;

      // qos / queue-group-templates / egress /
      container egress {
        tailf:info "Configure QoS egress queue groups";
        tailf:cli-add-mode;
        list queue-group {
          tailf:info "Configure QoS egress queue-group";
          tailf:cli-embed-no-on-delete;
          key queue-group-name;
          uses queue-group-template-entry;
        }
      }

      // qos / queue-group-templates / ingress /
      container ingress {
        tailf:info "Configure QoS ingress queue groups";
        tailf:cli-add-mode;

        list queue-group {
          tailf:info "Configure QoS ingress queue-group";
          tailf:cli-embed-no-on-delete;
          key queue-group-name;
          uses queue-group-template-entry;
        }
      }
    }

    // qos / scheduler-policy * /
    list scheduler-policy {
      //tailf:cli-recursive-delete;
      tailf:cli-embed-no-on-delete;
      key scheduler-policy-name;
      leaf scheduler-policy-name {
        type string;
      }
      leaf create {
        mandatory true;
        type empty;
        tailf:cli-hide-in-submode;
        tailf:cli-no-name-on-delete;
      }
      // qos / scheduler-policy * / description
      leaf description {
        tailf:cli-no-value-on-delete;
        type string;
      }
      // qos / scheduler-policy * / frame-based-accounting
      leaf frame-based-accounting {
        type empty;
      }
      // qos / scheduler-policy * / tier * /
      list tier {
        tailf:cli-recursive-delete;
        tailf:cli-embed-no-on-delete;
        key tier;
        leaf tier {
          type string;
        }

        // qos / scheduler-policy * / tier * / scheduler *
        list scheduler {
          tailf:cli-recursive-delete;
          tailf:cli-embed-no-on-delete;
          key scheduler-name;
          leaf scheduler-name {
            type string;
          }
          leaf create {
            mandatory true;
            type empty;
            tailf:cli-hide-in-submode;
            tailf:cli-no-name-on-delete;
          }
          leaf description {
            tailf:cli-embed-no-on-delete;
            tailf:cli-no-value-on-delete;
            type string;
          }
          // qos / scheduler-policy * / tier * / scheduler * / parent
          container parent {
            presence present;
            // tailf:cli-sequence-commands;
            tailf:cli-compact-syntax;
            tailf:cli-full-no;
            tailf:cli-recursive-delete;
            tailf:cli-embed-no-on-delete;
            leaf scheduler-name {
              tailf:cli-drop-node-name;
              tailf:cli-no-value-on-delete;
              tailf:cli-delete-container-on-delete;
              //mandatory true;
              type leafref {
                path "/alu:qos/scheduler-policy/tier/scheduler/scheduler-name";
              }
            }
            leaf weight {
              tailf:cli-no-name-on-delete;
              tailf:cli-no-value-on-delete;
              //tailf:cli-hide-in-submode;
              type string;
            }
            leaf level {
              //tailf:cli-hide-in-submode;
              tailf:cli-no-name-on-delete;
              tailf:cli-no-value-on-delete;

              type string;
            }
            leaf cir-weight {
              //tailf:cli-hide-in-submode;
              tailf:cli-no-name-on-delete;
              tailf:cli-no-value-on-delete;

              type string;
            }
            leaf cir-level {
              //tailf:cli-hide-in-submode;
              tailf:cli-no-name-on-delete;
              tailf:cli-no-value-on-delete;

              type string;
            }
          }
          // qos / scheduler-policy * / tier * / scheduler * / port-parent
          container port-parent {
            presence present;
            tailf:cli-compact-syntax;

            leaf weight {
              tailf:cli-no-name-on-delete;
              tailf:cli-no-value-on-delete;
              //tailf:cli-hide-in-submode;
              type string;
            }
            leaf level {
              tailf:cli-no-name-on-delete;
              tailf:cli-no-value-on-delete;
              //tailf:cli-hide-in-submode;
              type string;
            }
            leaf cir-weight {
              tailf:cli-no-name-on-delete;
              tailf:cli-no-value-on-delete;
              //tailf:cli-hide-in-submode;
              type string;
            }
            leaf cir-level {
              tailf:cli-no-name-on-delete;
              tailf:cli-no-value-on-delete;
              //tailf:cli-hide-in-submode;
              type string;
            }
          }
          container rate {
            presence present;
            tailf:cli-sequence-commands;
            tailf:cli-compact-syntax;
            tailf:cli-full-no;
            tailf:cli-recursive-delete;
            tailf:cli-embed-no-on-delete;
            leaf pir-rate {
              tailf:cli-drop-node-name;
              tailf:cli-delete-container-on-delete;
              mandatory true;
              type string;
            }
            leaf cir {
              //tailf:cli-hide-in-submode;
              tailf:cli-no-name-on-delete;
              tailf:cli-no-value-on-delete;

              type string;
            }
          }
          container mbs {
            tailf:cli-compact-syntax;
            leaf size {
              tailf:cli-drop-node-name;
              type uint32 {
                range "0..4194304";
              }
            }
            leaf unit {
              tailf:cli-drop-node-name;
              type enumeration {
                enum bytes;
                enum kilobytes;
              }
            }
          }
        }
      }
    }
    list shared-queue {
      tailf:cli-recursive-delete;
      tailf:cli-embed-no-on-delete;
      key policy-name;
      leaf policy-name {
        type string;
      }
      leaf create {
        mandatory true;
        type empty;
        tailf:cli-hide-in-submode;
        tailf:cli-no-name-on-delete;
      }
      leaf description {
        tailf:cli-embed-no-on-delete;
        tailf:cli-no-value-on-delete;
        type string;
      }
      container fc {
        presence present;
        tailf:cli-sequence-commands;
        tailf:cli-compact-syntax;
        tailf:cli-full-no;
        tailf:cli-recursive-delete;
        tailf:cli-embed-no-on-delete;
        leaf fc-name {
          tailf:cli-drop-node-name;
          tailf:cli-delete-container-on-delete;
          mandatory true;
          type string;
        }
        leaf broadcast-queue {
          type string;
        }
        leaf multicast-queue {
          type string;
        }
        leaf queue {
          type string;
        }
        leaf unknown-queue {
          type string;
        }
      }
      list queue {
        tailf:cli-recursive-delete;
        tailf:cli-embed-no-on-delete;
        key queue-id;
        leaf queue-id {
          type string;
        }
        leaf queue-type {
          tailf:cli-hide-in-submode;
          tailf:cli-drop-node-name;
          tailf:cli-no-name-on-delete;
          type string;
        }
        leaf multipoint {
          tailf:cli-hide-in-submode;
          type empty;
        }
        leaf create {
          mandatory true;
          type empty;
          tailf:cli-hide-in-submode;
          tailf:cli-no-name-on-delete;
        }
        leaf cbs {
          type string;
        }
        leaf high-prio-only {
          type string;
        }
        leaf mbs {
          type string;
        }
        leaf pool {
          type string;
        }
        container rate {
          presence present;
          tailf:cli-sequence-commands;
          tailf:cli-compact-syntax;
          tailf:cli-full-no;
          tailf:cli-recursive-delete;
          tailf:cli-embed-no-on-delete;
          leaf percent {
            tailf:cli-drop-node-name;
            tailf:cli-delete-container-on-delete;
            mandatory true;
            type string;
          }
          leaf cir {
            tailf:cli-hide-in-submode;
            type string;
          }
        }
      }
    }
    list mpls-lsp-exp-profile-map {
      tailf:info "Configure mpls-lsp-exp-profile-map policy";
      tailf:cli-embed-no-on-delete;
      key policy-id;

      leaf policy-id {
        type uint16 {
          range "1..65535";
        }
      }

      leaf create {
        mandatory true;
        type empty;
        tailf:cli-hide-in-submode;
        tailf:cli-no-name-on-delete;
      }

      leaf description {
        tailf:cli-embed-no-on-delete;
        tailf:cli-no-value-on-delete;
        type string;
      }

      container lsp-exp {
        tailf:cli-embed-no-on-delete;
        leaf lsp-exp-value {
          tailf:cli-drop-node-name;
          tailf:cli-no-value-on-delete;
          type uint8 {
            range "0..7";
          }
        }
        leaf profile {
          tailf:cli-no-name-on-delete;
          tailf:cli-no-value-on-delete;
          type enumeration {
            enum in;
            enum out;
          }
        }
      }
    }

    // qos / sap-egress * /
    list sap-egress {
      tailf:cli-embed-no-on-delete;
      tailf:cli-diff-dependency "/alu:qos/scheduler-policy";
      key policy-id;
      leaf policy-id {
        type uint16 {
          range "1 .. 65535";
          tailf:info "<policy-id>;;[1..65535]";
        }
      }
      leaf policy-name {
        tailf:cli-no-value-on-delete;
        type string;
      }
      // qos / sap-egress * / create
      leaf create {
        mandatory true;
        type empty;
        tailf:cli-hide-in-submode;
        tailf:cli-no-name-on-delete;
      }
      // qos / sap-egress * / description
      leaf description {
        tailf:cli-embed-no-on-delete;
        tailf:cli-no-value-on-delete;
        type string;
      }
      // qos / sap-egress * / queue *
      list queue {
        tailf:cli-embed-no-on-delete;
        key queue-id;
        leaf queue-id {
          type string;
        }
        // qos / sap-egress * / queue * type
        leaf queue-type {
          tailf:cli-hide-in-submode;
          tailf:cli-drop-node-name;
          tailf:cli-no-name-on-delete;
          type enumeration {
            enum expedite;
            enum best-effort;
            enum auto-expedite;
          }
        }
        // qos / sap-egress * / queue * create
        leaf create {
          mandatory true;
          type empty;
          tailf:cli-hide-in-submode;
          tailf:cli-no-name-on-delete;
        }
        // qos / sap-ingress * / queue * / adaption-rule
        container adaptation-rule {
          tailf:info "Specify the CIR and PIR adaptation rules";
          tailf:cli-compact-syntax;
          leaf pir {
            tailf:cli-no-name-on-delete;
            tailf:cli-no-value-on-delete;
            type enumeration {
              enum max;
              enum min;
              enum closest;
            }
          }
          leaf cir {
            tailf:cli-no-name-on-delete;
            tailf:cli-no-value-on-delete;
            type enumeration {
              enum max;
              enum min;
              enum closest;
            }
          }
        }

        // qos / sap-egress * / queue * / parent
        container parent {
          tailf:cli-compact-syntax;
          tailf:cli-sequence-commands {
            tailf:cli-reset-all-siblings;
          }
          leaf scheduler-name {
            tailf:cli-drop-node-name;
            tailf:cli-no-value-on-delete;
            type string;
          }
          leaf weight {
            tailf:cli-break-sequence-commands;
            tailf:cli-no-value-on-delete;
            tailf:cli-no-name-on-delete;
            type uint8 {
              range "0..100";
            }
          }
          leaf level {
            tailf:cli-no-value-on-delete;
            tailf:cli-no-name-on-delete;
            type uint8 {
              range "1..8";
            }
          }
          leaf cir-weight {
            tailf:cli-no-value-on-delete;
            tailf:cli-no-name-on-delete;
            type uint8 {
              range "0..100";
            }
          }
          leaf cir-level {
            tailf:cli-no-value-on-delete;
            tailf:cli-no-name-on-delete;
            type uint8 {
              range "0..8";
            }
          }
        }

        container port-parent {
          tailf:cli-compact-syntax;
          leaf weight {
            type uint8 {
              range "0..100";
            }
          }
          leaf level {
            type uint8 {
              range "1..8";
            }
          }
          leaf cir-weight {
            type uint8 {
              range "0..100";
            }
          }
          leaf cir-level {
            type uint8 {
              range "0..8";
            }
          }
        }
        container rate {
          tailf:cli-sequence-commands;
          tailf:cli-compact-syntax;
          tailf:cli-full-no;
          tailf:cli-embed-no-on-delete;
          leaf pir-rate {
            tailf:cli-drop-node-name;
            tailf:cli-delete-container-on-delete;
            type union {
              type enumeration {
                enum max;
              }
              type uint32 {
                range "1..100000000";
              }
            }
          }
          leaf cir {
            type union {
              type enumeration {
                enum max;
              }
              type uint32 {
                range "0..100000000";
              }
            }
          }
        }

        container cbs {
          tailf:cli-compact-syntax;
          leaf size {
            tailf:cli-drop-node-name;
            tailf:cli-no-value-on-delete;
            type uint32 {
              range "0..4194304";
            }
          }
        }

        container mbs {
          tailf:cli-compact-syntax;
          leaf size {
            tailf:cli-drop-node-name;
            tailf:cli-no-value-on-delete;
            type uint32 {
              range "0..4194304";
            }
          }
          leaf unit {
            tailf:cli-drop-node-name;
            type enumeration {
              enum bytes;
              enum kilobytes;
            }
          }
        }

        // qos / sap-egress * / burst-limit
        container burst-limit {
          tailf:info "Specify burst-limit";
          tailf:cli-embed-no-on-delete;
          tailf:cli-compact-syntax;
          tailf:cli-sequence-commands;

          leaf size {
            tailf:cli-drop-node-name;
            tailf:cli-no-value-on-delete;
            type union {
              type uint32 {
                range "0..4194304";
              }
              type enumeration {
                enum default;
              }
            }
          }

          leaf unit {
            tailf:cli-drop-node-name;
            tailf:cli-no-value-on-delete;
            type enumeration {
              enum bytes;
              enum kilobytes;
            }
          }
        }

        // qos / sap-egress * / queue * / xp-specific
        container xp-specific {
          tailf:info "Configure IOM3-XP specific information";
          tailf:cli-add-mode;

          container wred-queue {
            tailf:info "Configure WRED queue";
            tailf:cli-embed-no-on-delete;
            tailf:cli-compact-syntax;
            tailf:cli-sequence-commands;

            leaf policy {
              tailf:info "max 32 chars;;slope-policy-name";
              tailf:cli-no-value-on-delete;
              tailf:cli-no-name-on-delete;
              type string;
            }
          }

          container packet-byte-offset {
            tailf:info "Specify packet byte offset";
            tailf:cli-embed-no-on-delete;
            tailf:cli-compact-syntax;
            tailf:cli-sequence-commands;

            choice a {
              leaf add {
                type uint8 {
                  range "0..32";
                }
              }
              leaf subtract {
                type uint8 {
                  range "0..64";
                }
              }
            }
          }
        }
      }

      list fc {
        tailf:cli-embed-no-on-delete;
        key fc-name;
        leaf fc-name {
          type string;
        }
        leaf create {
          tailf:cli-hide-in-submode;
          tailf:cli-no-name-on-delete;
          mandatory true;
          type empty;
        }
        leaf queue {
          type string;
        }
        container dot1p {
          tailf:cli-compact-syntax;
          tailf:cli-sequence-commands;
          choice dot1p-choice {
            case a {
              leaf dot1p-value {
                tailf:cli-drop-node-name;
                type uint8 {
                  range "0..7";
                }
              }
            }
            case b {
              leaf in-profile {
                type uint8 {
                  range "0..7";
                }
              }
              leaf out-profile {
                type uint8 {
                  range "0..7";
                }
              }
            }
          }
        }
      }

      container ip-criteria {
        tailf:cli-add-mode;
        uses ip-criteria-grouping;
      }

      container ipv6-criteria {
        tailf:cli-add-mode;
        uses ipv6-criteria-grouping;
      }

      list dscp {
        tailf:cli-suppress-mode;
        key id;
        tailf:cli-compact-syntax;
        leaf id {
          type dscp-type;
        }
        leaf fc {
          type string;
        }
        leaf priority {
          type enumeration {
            enum high;
            enum low;
          }
        }
      }
    }
   // qos / sap-ingress *
    list sap-ingress {
      tailf:cli-embed-no-on-delete;
      tailf:cli-diff-dependency "/alu:qos/scheduler-policy";
      key policy-id;
      leaf policy-id {
        type uint16 {
          range "1 .. 65535";
          tailf:info "<policy-id>;;[1..65535]";
        }
      }
      // qos / sap-ingress * / description
      leaf description {
        tailf:cli-embed-no-on-delete;
        tailf:cli-no-value-on-delete;
        type string;
      }
      // qos / sap-ingress * / policy-name
      leaf policy-name {
        tailf:cli-no-value-on-delete;
        type string;
      }
      // qos / sap-ingress * / create
      leaf create {
        mandatory true;
        type empty;
        tailf:cli-hide-in-submode;
        tailf:cli-no-name-on-delete;
      }
      // qos / sap-ingress * / meter
      list meter {
        tailf:info "Configure a meter";
        tailf:cli-embed-no-on-delete;
        key meter-id;
        uses meter-grouping;
      }
      // qos / sap-ingress * / num-qos-classifiers
      container num-qos-classifiers {
        tailf:info "Configure number of classfiers and meters for this policy";
        tailf:cli-embed-no-on-delete;
        tailf:cli-compact-syntax;

        leaf num-resources {
          tailf:cli-drop-node-name;
          tailf:cli-no-value-on-delete;
          type uint16 {
            range "1..256";
          }
        }

        leaf keyword {
          tailf:cli-drop-node-name;
          tailf:cli-no-value-on-delete;
          type enumeration {
            enum ipv6;
            enum no-ipv6;
          }
        }
      }
      // qos / sap-ingress * / prec
      list prec {
        key ip-prec-value;
        tailf:info "Specify IP precedence mappings";
        tailf:cli-compact-syntax;
        tailf:cli-suppress-mode;
        leaf ip-prec-value {
          tailf:cli-drop-node-name;
          type uint16 {
            range "0..7";
          }
        }
        // qos / sap-ingress * / prec * / fc
        leaf fc {
          type enumeration {
            enum be;
            enum l2;
            enum af;
            enum l1;
            enum h2;
            enum ef;
            enum h1;
            enum nc;
          }
        }
        // qos / sap-ingress * / prec * / priority
        leaf priority {
          type enumeration {
            enum low;
            enum high;
          }
        }
      }
      // qos / sap-ingress * / queue
      list queue {
        tailf:cli-embed-no-on-delete;
        key queue-id;
        leaf queue-id {
          type string;
        }
        // qos / sap-ingress * / queue * / multipoint
        leaf multipoint {
          tailf:cli-hide-in-submode;
          type empty;
        }
        // qos / sap-ingress * / queue * / queue-type

        leaf queue-type {
          tailf:cli-hide-in-submode;
          tailf:cli-drop-node-name;
          tailf:cli-no-name-on-delete;
          type string;
        }
        leaf queue-mode {
          tailf:cli-hide-in-submode;
          tailf:cli-drop-node-name;
          tailf:cli-no-name-on-delete;
          type string;
        }
        leaf create {
          mandatory true;
          type empty;
          tailf:cli-hide-in-submode;
          tailf:cli-no-name-on-delete;
        }
        // qos / sap-ingress * / queue * / adaption-rule
        container adaptation-rule {
          tailf:info "Specify the CIR and PIR adaptation rules";
          tailf:cli-compact-syntax;
          leaf pir {
            tailf:cli-no-name-on-delete;
            tailf:cli-no-value-on-delete;
            type enumeration {
              enum max;
              enum min;
              enum closest;
            }
          }
          leaf cir {
            tailf:cli-no-name-on-delete;
            tailf:cli-no-value-on-delete;
            type enumeration {
              enum max;
              enum min;
              enum closest;
            }
          }
        }
        // qos / sap-ingress * / parent
        container parent {
          tailf:cli-compact-syntax;
          tailf:cli-sequence-commands {
            tailf:cli-reset-all-siblings;
          }
          leaf scheduler-name {
            tailf:cli-drop-node-name;
            tailf:cli-no-value-on-delete;
            type string;
          }
          leaf weight {
            tailf:cli-break-sequence-commands;
            tailf:cli-no-value-on-delete;
            tailf:cli-no-name-on-delete;
            type uint8 {
              range "0..100";
            }
          }
          leaf level {
            tailf:cli-no-value-on-delete;
            tailf:cli-no-name-on-delete;
            type uint8 {
              range "1..8";
            }
          }
          leaf cir-weight {
            tailf:cli-no-value-on-delete;
            tailf:cli-no-name-on-delete;
            type uint8 {
              range "0..100";
            }
          }
          leaf cir-level {
            tailf:cli-no-value-on-delete;
            tailf:cli-no-name-on-delete;
            type uint8 {
              range "0..8";
            }
          }
        }

        container cbs {
          tailf:cli-compact-syntax;
          leaf size {
            tailf:cli-drop-node-name;
            tailf:cli-no-value-on-delete;
            type uint32 {
              range "0..4194304";
            }
          }
        }

        container mbs {
          tailf:cli-compact-syntax;
          leaf size {
            tailf:cli-drop-node-name;
            tailf:cli-no-value-on-delete;
            type uint32 {
              range "0..4194304";
            }
          }
          leaf unit {
            tailf:cli-drop-node-name;
            type enumeration {
              enum bytes;
              enum kilobytes;
            }
          }
        }

        container rate {
          tailf:cli-sequence-commands;
          tailf:cli-compact-syntax;
          tailf:cli-full-no;
          tailf:cli-embed-no-on-delete;
          leaf pir-rate {
            tailf:cli-drop-node-name;
            tailf:cli-delete-container-on-delete;
            type string;
          }
          leaf cir {
            type string;
          }
        }
      }
      // qos / sap-ingress * / fc *
      list fc {
        tailf:cli-embed-no-on-delete;
        key fc-name;
        leaf fc-name {
          type string;
        }
        leaf create {
          mandatory true;
          type empty;
          tailf:cli-hide-in-submode;
          tailf:cli-no-name-on-delete;
        }
        leaf queue {
          type string;
        }

        container broadcast-queue {
          tailf:cli-compact-syntax;
          tailf:cli-sequence-commands;
          leaf id {
            tailf:cli-drop-node-name;
            type uint8 {
              range "1..32";
            }
          }
          leaf group {
            type string;
          }
        }

        container multicast-queue {
          tailf:cli-compact-syntax;
          tailf:cli-sequence-commands;
          leaf id {
            tailf:cli-drop-node-name;
            type uint8 {
              range "1..32";
            }
          }
          leaf group {
            type string;
          }
        }


        container unknown-queue {
          tailf:cli-compact-syntax;
          tailf:cli-sequence-commands;
          leaf id {
            tailf:cli-drop-node-name;
            type uint8 {
              range "1..32";
            }
          }
          leaf group {
            type string;
          }
        }

        leaf broadcast-meter {
          tailf:info "Specify the broadcast-meter";
          tailf:cli-embed-no-on-delete;
          tailf:cli-no-value-on-delete;
          type leafref {
            path "../../meter/meter-id";
          }
        }

        leaf meter {
          tailf:info "Specify the unicast-meter";
          tailf:cli-embed-no-on-delete;
          tailf:cli-no-value-on-delete;
          type leafref {
            path "../../meter/meter-id";
          }
        }

        leaf multicast-meter {
          tailf:info "Specify the multicast-meter";
          tailf:cli-embed-no-on-delete;
          tailf:cli-no-value-on-delete;
          type leafref {
            path "../../meter/meter-id";
          }
        }

        leaf unknown-meter {
          tailf:info "Specify the unknown-meter";
          tailf:cli-embed-no-on-delete;
          tailf:cli-no-value-on-delete;
          type leafref {
            path "../../meter/meter-id";
          }
        }

        container in-remark {
          choice remark-choice {
            leaf dscp {
              type dscp-type;
            }
            leaf prec {
              type uint8 {
                range "0..7";
              }
            }
          }
        }
        container out-remark {
          choice remark-choice {
            leaf dscp {
              type dscp-type;
            }
            leaf prec {
              type uint8 {
                range "0..7";
              }
            }
          }
        }

        container policer {
          tailf:cli-compact-syntax;
          tailf:cli-sequence-commands;
          leaf id {
            tailf:cli-drop-node-name;
            type uint8 {
              range "1..32";
            }
          }
          leaf fp-redirect-group {
            tailf:cli-drop-node-name;
            type string;
          }
        }
      }

      container ip-criteria {
        tailf:cli-add-mode;
        uses ip-criteria-grouping;
      }

      container ipv6-criteria {
        tailf:cli-add-mode;
        uses ipv6-criteria-grouping;
      }

      // qos / sap-ingress * / default-fc
      leaf default-fc {
        tailf:info "Configure default forwarding class for this policy";
        type string;
      }

      // qos / sap-ingress * / default-priority
      leaf default-priority {
        tailf:info "Configure default priority for this policy";
        type enumeration {
          enum "low";
          enum "high";
        }
      }

      list dot1p {
        tailf:cli-suppress-mode;
        key id;
        tailf:cli-compact-syntax;
        leaf id {
          type uint8 {
            range "0..7";
          }
        }
        leaf fc {
          type string;
        }
        leaf priority {
          type enumeration {
            enum high;
            enum low;
          }
        }
      }
      list dscp {
        tailf:cli-suppress-mode;
        key id;
        tailf:cli-compact-syntax;
        leaf id {
          type dscp-type;
        }
        leaf fc {
          type string;
        }
        leaf priority {
          type enumeration {
            enum high;
            enum low;
          }
        }
      }

      list policer {
        tailf:cli-embed-no-on-delete;

        key id;
        leaf id {
          type uint8 {
            range "1..32";
          }
        }

        leaf create {
          mandatory true;
          type empty;
          tailf:cli-hide-in-submode;
          tailf:cli-no-name-on-delete;
        }

        container rate {
          tailf:cli-compact-syntax;
          leaf pir {
            tailf:cli-drop-node-name;
            type union {
              type uint32;
              type enumeration {
                enum max;
              }
            }
          }
          leaf cir {
            type union {
              type uint32;
              type enumeration {
                enum max;
              }
            }
          }
        }
        container cbs {
          tailf:cli-compact-syntax;
          leaf size {
            tailf:cli-drop-node-name;
            tailf:cli-no-value-on-delete;
            type uint32 {
              range "0..4194304";
            }
          }
        }
        container mbs {
          tailf:cli-compact-syntax;
          leaf size {
            tailf:cli-drop-node-name;
            tailf:cli-no-value-on-delete;
            type uint32 {
              range "0..4194304";
            }
          }
          leaf unit {
            tailf:cli-drop-node-name;
            type enumeration {
              enum bytes;
              enum kilobytes;
            }
          }
        }
      }
    }

    // qos / network *
    list network {
      tailf:cli-embed-no-on-delete;
      key id;

      leaf id {
        type uint16;
      }

      leaf network-policy-type {
        tailf:cli-hide-in-submode;
        tailf:cli-no-name-on-delete;
        tailf:cli-no-value-on-delete;
        type enumeration {
          enum ip-interface;
          enum port;
        }
      }

      leaf create {
        mandatory true;
        type empty;
        tailf:cli-hide-in-submode;
        tailf:cli-no-name-on-delete;
      }

      leaf description {
        tailf:cli-embed-no-on-delete;
        tailf:cli-no-value-on-delete;
        type string;
      }

      // qos / network * / ingress
      container ingress {
        tailf:cli-add-mode;
        list dscp {
          tailf:cli-compact-syntax;
          tailf:cli-suppress-mode;
          key id;

          leaf id {
            type dscp-type;
          }
          leaf fc {
            tailf:cli-no-name-on-delete;
            tailf:cli-no-value-on-delete;
            type string;
          }
          leaf profile {
            tailf:cli-no-name-on-delete;
            tailf:cli-no-value-on-delete;
            type enumeration {
              enum in;
              enum out;
            }
          }
        }
        list lsp-exp {
          tailf:cli-compact-syntax;
          tailf:cli-suppress-mode;
          key id;
          leaf id {
            type uint8 {
              range "0..7";
            }
          }
          leaf fc {
            type enumeration {
              enum be;
              enum l2;
              enum af;
              enum l1;
              enum h2;
              enum ef;
              enum h1;
              enum nc;
            }
          }
          leaf profile {
            type enumeration {
              enum in;
              enum out;
            }
          }
        }
        container default-action {
          tailf:cli-compact-syntax;
          leaf fc {
            type enumeration {
              enum be;
              enum l2;
              enum af;
              enum l1;
              enum h2;
              enum ef;
              enum h1;
              enum nc;
            }
          }
          leaf profile {
            type enumeration {
              enum in;
              enum out;
            }
          }
        }

        list meter {
          tailf:info "Configure a meter";
          tailf:cli-embed-no-on-delete;
          key meter-id;
          uses meter-grouping;
        }

        leaf mpls-lsp-exp-profile {
          tailf:info "Configure mpls-lsp-exp-profile policy";
          tailf:cli-no-value-on-delete;
          type uint16 {
            range "1..65535";
          }
        }

        list fc {
          tailf:info "Configure forwarding-class to meter mappings";
          tailf:cli-embed-no-on-delete;
          key class;

          leaf class {
            type string;
          }

          leaf create {
            mandatory true;
            type empty;
            tailf:cli-hide-in-submode;
            tailf:cli-no-name-on-delete;
          }

          leaf meter {
            tailf:cli-embed-no-on-delete;
            tailf:cli-no-value-on-delete;
            type uint8 {
              range "1..12";
            }
          }

          leaf multicast-meter {
            tailf:cli-embed-no-on-delete;
            tailf:cli-no-value-on-delete;
            type uint8 {
              range "1..12";
            }
          }
        }
      }
      // qos / network * / egress
      container egress {
        tailf:cli-add-mode;
        list fc {
          key id;
          leaf id {
            type enumeration {
              enum be;
              enum l2;
              enum af;
              enum l1;
              enum h2;
              enum ef;
              enum h1;
              enum nc;
            }
          }
          leaf dscp-in-profile {
            type dscp-type;
          }
          leaf dscp-out-profile {
            type dscp-type;
          }
          leaf lsp-exp-in-profile {
            type uint8 {
              range "0..7";
            }
          }
          leaf lsp-exp-out-profile {
            type uint8 {
              range "0..7";
            }
          }
          leaf dot1p-in-profile {
            type uint8 {
              range "0..7";
            }
          }
          leaf dot1p-out-profile {
            type uint8 {
              range "0..7";
            }
          }

        }
        container remarking {
          presence true;
          leaf force {
            type empty;
          }
        }
        container prec {
          tailf:cli-compact-syntax;
          leaf prec-value {
            tailf:cli-drop-node-name;
            type uint8 {
              range "0..7";
            }
          }
          leaf fc {
            type enumeration {
              enum be;
              enum l2;
              enum af;
              enum l1;
              enum h2;
              enum ef;
              enum h1;
              enum nc;
            }
          }
          leaf profile {
            type enumeration {
              enum in;
              enum out;
            }
          }
        }
        list dscp {
          tailf:cli-compact-syntax;
          tailf:cli-suppress-mode;
          key id;

          leaf id {
            type dscp-type;
          }
          leaf fc {
            tailf:cli-no-name-on-delete;
            tailf:cli-no-value-on-delete;
            type string;
          }
          leaf profile {
            tailf:cli-no-name-on-delete;
            tailf:cli-no-value-on-delete;
            type enumeration {
              enum in;
              enum out;
            }
          }
        }
      }
    }

    // qos / slope-policy *
    list slope-policy {
      tailf:info "Configure a slope-policy";
      key name;
      leaf name {
        type string;
      }
      // qos / slope-policy * / create
      leaf create {
        mandatory true;
        type empty;
        tailf:cli-hide-in-submode;
        tailf:cli-no-name-on-delete;
      }
      // qos / slope-policy * / description
      leaf description {
        tailf:info "Description for the slope policy policy";
        tailf:cli-no-value-on-delete;
        type string {
          length "1..80";
        }
      }
      // qos / slope-policy * / high-slope
      container high-slope {
        tailf:info "Configure high-prio RED slope parameters";
        tailf:cli-add-mode;

        // qos / slope-policy * / high-slope / start-avg
        leaf start-avg {
          tailf:info "Configure starting average";
          tailf:cli-no-value-on-delete;
          type uint8 {
            range "0..100";
          }
        }
        // qos / slope-policy * / high-slope / max-avg
        leaf max-avg {
          tailf:info "Configure max average";
          tailf:cli-no-value-on-delete;
          type uint8 {
            range "0..100";
          }
        }
        // qos / slope-policy * / high-slope / max-prob
        leaf max-prob {
          tailf:info "Configure max probability";
          tailf:cli-no-value-on-delete;
          type uint8 {
            range "0..100";
          }
        }
        // qos / slope-policy * / high-slope / shutdown
        leaf shutdown {
          tailf:info "Administratively enable/disable high slope";
          tailf:cli-boolean-no;
          default true;
          type boolean;
        }
      }
      // qos / slope-policy * / low-slope
      container low-slope {
        tailf:info "Configure low-prio RED slope parameters";
        tailf:cli-add-mode;
        // qos / slope-policy * / low-slope / start-avg
        leaf start-avg {
          tailf:info "Configure starting average";
          tailf:cli-no-value-on-delete;
          type uint8 {
            range "0..100";
          }
        }
        // qos / slope-policy * / low-slope / max-avg
        leaf max-avg {
          tailf:info "Configure max average";
          tailf:cli-no-value-on-delete;
          type uint8 {
            range "0..100";
          }
        }
        // qos / slope-policy * / low-slope / max-prob
        leaf max-prob {
          tailf:info "Configure max probability";
          tailf:cli-no-value-on-delete;
          type uint8 {
            range "0..100";
          }
        }
        // qos / slope-policy * / low-slope / shutdown
        leaf shutdown {
          tailf:info "Administratively enable/disable low slope";
          tailf:cli-boolean-no;
          default true;
          type boolean;
        }
      }
    }

    // qos / port-scheduler-policy *
    list port-scheduler-policy {
      tailf:info "Configure a port scheduler policy";
      key name;
      leaf name {
        type string;
      }
      // qos / port-scheduler-policy * / description
      leaf description {
        tailf:info "Description for this policy";
        tailf:cli-no-value-on-delete;
        type string;
      }

      // qos / port-scheduler-policy * / level
      list level {
        tailf:info "Configure priority level parameters";
        tailf:cli-suppress-mode;
        tailf:cli-compact-syntax;
        key priority-level;
        leaf priority-level {
          type uint8 {
            range "1..8";
          }
        }
        leaf rate {
          type uint32;
        }
        leaf cir {
          type uint32;
        }
      }
      // qos / port-scheduler-policy * / max-rate
      leaf max-rate {
        tailf:info "Configure the maximum rate";
        type uint32 {
          range "1..3200000000";
        }
      }

      // qos / port-scheduler-policy * / orphan-override
      container orphan-override {
        tailf:info "Configure port scheduler policy orphan settings";
        tailf:cli-compact-syntax;
        leaf level {
          type uint8 {
            range "1..8";
          }
        }
      }

      // qos / port-scheduler-policy * / create
      leaf create {
        mandatory true;
        type empty;
        tailf:cli-hide-in-submode;
        tailf:cli-no-name-on-delete;
      }
    }

    // qos / policer-control-policy *
    list policer-control-policy {
      tailf:info "Configure Qos Policer control Policy";
      tailf:cli-embed-no-on-delete;
      key name;
      leaf name {
        type string {
          length "1..32";
        }
      }

      // qos / policer-control-policy * / description
      leaf description {
        tailf:info "Description for this policy";
        tailf:cli-no-value-on-delete;
        type string;
      }

      // qos / policer-control-policy * / root
      container root {
        tailf:info "Specify Root Configuration";
        tailf:cli-embed-no-on-delete;
        tailf:cli-add-mode;

        leaf max-rate {
          tailf:info "Configure Max Rate in kilobits-per-second";
          tailf:cli-no-value-on-delete;
          type union {
            type uint32 {
              range "1..20000000";
            }
            type enumeration {
              enum max;
            }
          }
        }
      }
      // qos / policer-control-policy * /  priority-mbs-thresholds
      container priority-mbs-thresholds {
        tailf:info "Configure priority mbs thresholds";
        tailf:cli-embed-no-on-delete;
        tailf:cli-add-mode;

        // qos / policer-control-policy * /  priority-mbs-thresholds
        // min-thresh-separation
        container min-thresh-separation {
          tailf:info "Configure min threshold separation";
          tailf:cli-sequence-commands;
          tailf:cli-compact-syntax;

          leaf size {
            tailf:cli-drop-node-name;
            tailf:cli-no-value-on-delete;
            type union {
              type uint32 {
                range "0..4194304";
              }
              type enumeration {
                enum default;
              }
            }
          }

          leaf unit {
            tailf:cli-drop-node-name;
            tailf:cli-no-value-on-delete;
            type enumeration {
              enum bytes;
              enum kilobytes;
            }
          }
        }

        // qos / policer-control-policy * /  priority-mbs-thresholds
        // priority
        list priority {
          tailf:info "Configure Priority Levels";
          tailf:cli-embed-no-on-delete;
          key level;
          leaf level {
            type uint8 {
              range "1..8";
            }
          }

          // qos / policer-control-policy * /  priority-mbs-thresholds
          // priority * / mbs-contribution
          container mbs-contribution {
            tailf:info "Configure mbs size";
            tailf:cli-compact-syntax;
            tailf:cli-sequence-commands;
            tailf:cli-embed-no-on-delete;

            leaf size {
              tailf:cli-drop-node-name;
              tailf:cli-no-value-on-delete;
              type union {
                type uint32 {
                  range "0..4194304";
                }
                type enumeration {
                  enum default;
                }
              }
            }

            leaf unit {
              tailf:cli-drop-node-name;
              tailf:cli-no-value-on-delete;
              type enumeration {
                enum bytes;
                enum kilobytes;
              }
            }

            leaf fixed {
              type empty;
            }
          }
        }
      }
      // qos / policer-control-policy * / create
      leaf create {
        mandatory true;
        type empty;
        tailf:cli-hide-in-submode;
        tailf:cli-no-name-on-delete;
      }
    }
    }


  /// ========================================================================
  /// eth-cfm /
  /// ========================================================================
  container eth-cfm {
    tailf:info "Configure CFM parameters";

    tailf:cli-add-mode;

    // eth-cfm / domain *
    list domain {
      tailf:info "Configure Connectivity Fault Management domain";
      tailf:cli-recursive-delete;
      tailf:cli-embed-no-on-delete;
      key id;

      leaf id {
        tailf:info "<md-index>;;<1..4294967295>";
        type uint32 {
          range "1..4294967295";
        }
      }

      // eth-cfm / domain * / format
      leaf format {
        tailf:info "<format>;;<dns|mac|none|string>";
        tailf:cli-hide-in-submode;
        tailf:cli-no-name-on-delete;
        tailf:cli-no-value-on-delete;
        type string;
      }

      // eth-cfm / domain * / level
      leaf level {
        tailf:info "<level>;;<0..7>";
        tailf:cli-hide-in-submode;
        tailf:cli-no-name-on-delete;
        tailf:cli-no-value-on-delete;
        type uint8 {
          range "0..7";
        }
      }

      // eth-cfm / domain * / name
      leaf name {
        tailf:info "<name>;;<string>";
        tailf:cli-hide-in-submode;
        tailf:cli-no-name-on-delete;
        tailf:cli-no-value-on-delete;
        type string;
      }

      list association {
        tailf:info "Configure a Maintenance Association for the Domain";
        tailf:cli-recursive-delete;
        tailf:cli-embed-no-on-delete;
        key ma-index;

        leaf ma-index {
          tailf:info "<ma-index>";
          type uint32 {
            range "1..4294967295";
          }
        }

        leaf format {
          tailf:info "{icc-based|integer|string|vid|vpn-id}";
          tailf:cli-hide-in-submode;
          tailf:cli-no-name-on-delete;
          tailf:cli-no-value-on-delete;
          type enumeration {
            enum icc-based;
            enum integer;
            enum string;
            enum vid;
            enum vpn-id;
          }
        }

        leaf name {
          tailf:info "Maintenance Association Name (1..45 characters)";
          tailf:cli-hide-in-submode;
          tailf:cli-no-name-on-delete;
          tailf:cli-no-value-on-delete;
          type string {
            length "1..45";
          }
        }

        container ccm-hold-time {
          tailf:info "Configure the CCM interval holding timers";
          tailf:cli-embed-no-on-delete;

          leaf down {
            type uint32;
          }
        }

        leaf ccm-interval {
          tailf:info "Configure the CCM transmission interval for all MEPs";
          tailf:cli-embed-no-on-delete;
          type enumeration {
            enum 10ms;
            enum 100ms;
            enum 1;
            enum 10;
            enum 60;
            enum 600;
          }
        }

        container remote-mepid {
          leaf mep-id {
            tailf:info "Configure the Remote MEP ID";
            tailf:cli-embed-no-on-delete;
            tailf:cli-drop-node-name;
            type uint16 {
              range "1..8191";
            }
          }

          leaf remote-mac {
            tailf:info "xx:xx:xx:xx:xx:xx or default";
            type union {
              type enumeration {
                enum default;
              }
              type ieee-mac;
            }
          }
        }

        list bridge-identifier {
          tailf:info "Configure the service ID for the association";
          tailf:cli-embed-no-on-delete;
          key id;

          leaf id {
            type uint32;
          }

          leaf mhf-creation {
            tailf:info "Configure the MIP Half Function (MHF)";
            tailf:cli-embed-no-on-delete;
            type enumeration {
              enum default;
              enum none;
              enum explicit;
            }
          }

          leaf vlan {
            tailf:info "Configure the Bridge-identifier Primary Vlan-Id";
            tailf:cli-embed-no-on-delete;
            type uint16 {
              range "0..4094";
            }
          }
        }
      }
    }
  }


  /// ========================================================================
  /// log /
  /// ========================================================================
  container log {
    tailf:info "Event stream logging configuration";
    tailf:cli-add-mode;

    // log / file-id *
    list file-id {
      tailf:cli-embed-no-on-delete;
      key id;
      leaf id {
        type uint32;
      }

      // log / file-id * / description
      leaf description {
        type string;
      }

      // log / file-id * / location
      leaf-list location {
        tailf:cli-flat-list-syntax;
        tailf:cli-no-value-on-delete;
        type string;
      }

      // log / file-id * / rollover
      container rollover {
        tailf:cli-embed-no-on-delete;
        tailf:cli-compact-syntax;
        tailf:cli-sequence-commands;

        leaf id {
          tailf:cli-drop-node-name;
          tailf:cli-no-value-on-delete;
          type uint32;
        }

        leaf retention {
          tailf:cli-no-value-on-delete;
          tailf:cli-no-name-on-delete;
          type uint32;
        }
      }
    }


    // log / accounting-policy * /
    list accounting-policy {
      tailf:info "Configure an accounting-policy";
      key acct-policy-id;
      leaf acct-policy-id {
        type uint16 {
          range "1..99";
        }
      }
      // log / accounting-policy * / collection-interval
      leaf collection-interval {
        tailf:cli-no-value-on-delete;
        tailf:info "Configure the accounting collection interval";
        type uint8 {
          range "0..120";
        }
      }
      // log / accounting-policy * / description
      leaf description {
        tailf:info "Description for this accounting policy";
        tailf:cli-no-value-on-delete;
        type string {
          length "1..80";
        }
      }
      // log / accounting-policy * / record
      leaf record {
        tailf:info "Configure the accounting record type to be forwarded "+
          "to the configured accounting file";
        type enumeration {
          enum aa-app-group;
          enum aa-application;
          enum aa-partition;
          enum aa-performance;
          enum aa-protocol;
          enum aa-subscriber-application;
          enum aa-subscriber-protocol;
          enum combined-ldp-lsp-egress;
          enum combined-mpls-lsp-egress;
          enum combined-mpls-lsp-ingress;
          enum combined-network-ing-egr-octets;
          enum combined-queue-group;
          enum combined-sdp-ingress-egress;
          enum combined-service-ing-egr-octets;
          enum combined-service-ingress;
          enum compact-service-ingress-octets;
          enum complete-pm;
          enum complete-sdp-ingress-egress;
          enum complete-service-ingress-egress;
          enum complete-subscriber-ingress-egress;
          enum custom-record-aa-sub;
          enum custom-record-service;
          enum custom-record-subscriber;
          enum network-egress-octets;
          enum network-egress-packets;
          enum network-ingress-octets;
          enum network-ingress-packets;
          enum queue-group-octets;
          enum queue-group-packets;
          enum saa;
          enum service-egress-octets;
          enum service-egress-packets;
          enum service-ingress-octets;
          enum service-ingress-packets;
          enum video;
          enum complete-ethernet-port;
          enum extended-service-ingress-egress;
          enum complete-network-ing-egr;
        }
      }
      // log / accounting-policy * / to
      container to {
        tailf:info "Specify log destination";
        tailf:cli-compact-syntax;
        leaf destination {
          tailf:cli-drop-node-name;
          type enumeration {
            enum file;
            enum no-file;
          }
        }
        // log / accounting-policy * / log-file-id
        leaf log-file-id {
          tailf:cli-drop-node-name;
          when "../destination = 'file'";
          type leafref{
            path "/alu:log/file-id/id";
          }
        }
      }

      // log / accounting-policy * / shutdown
      leaf shutdown {
        tailf:cli-boolean-no;
        default true;
        type boolean;
      }
    }


    // log / event-control *
    list event-control {
      tailf:cli-suppress-mode;
      tailf:cli-embed-no-on-delete;
      tailf:cli-compact-syntax;
      tailf:cli-sequence-commands;
      key name;
      leaf name {
        type string;
      }

      // log / event-control * / year
      leaf year {
        tailf:cli-drop-node-name;
        tailf:cli-no-value-on-delete;
        type uint32;
      }

      // log / event-control * / generate
      leaf generate {
        tailf:cli-no-name-on-delete;
        type empty;
      }

      // log / event-control * / throttle
      leaf throttle {
        tailf:cli-no-name-on-delete;
        type empty;
      }
    }

    // log / filter *
    list filter {
      tailf:info "Configure an event filter";
      tailf:cli-embed-no-on-delete;
      key filter-id;
      leaf filter-id {
        type uint16 {
          range "1..1001";
        }
      }
      // log / filter * / default-action
      leaf default-action {
        tailf:info "Specify the default action for the event filter";
        tailf:cli-no-value-on-delete;
        type enumeration {
          enum drop;
          enum forward;
        }
      }

      // log / filter * / description
       leaf description {
         tailf:info "Description string for the event filter";
         tailf:cli-no-value-on-delete;
         type string;
       }
       // log / filter * / entry *
       list entry {
         tailf:info "Configure an event filter entry";
         tailf:cli-embed-no-on-delete;
         key entry-id;
         leaf entry-id {
           type uint16 {
             range "1..999";
           }
         }
         // log / filter * / entry *
         leaf action {
           tailf:info "Specify the action for this event filter entry";
           tailf:cli-no-value-on-delete;
           type enumeration {
             enum drop;
             enum forward;
           }
         }
         // log / filter * / entry * / description
        leaf description {
          tailf:info "Description for this event filter entry";
          tailf:cli-no-value-on-delete;
          type string;
        }
        // log / filter * / entry * / match *
        container match {
          tailf:info "Specify match conditions for this event filter entry";
          tailf:cli-embed-no-on-delete;
          tailf:cli-add-mode;
          // log / filter * / entry * / match * / application
          container application {
              tailf:info "Specify application id to match";
              tailf:cli-compact-syntax;
              tailf:cli-sequence-commands;
              tailf:cli-embed-no-on-delete;
              // log / filter * / entry * / match * / application rule
              leaf rule {
                tailf:cli-drop-node-name;
                tailf:cli-no-value-on-delete;
                type enumeration {
                  enum eq;
                  enum neq;
                }
              }
              // log / filter * / entry * / match * / application application-id
              leaf application-id {
                tailf:cli-drop-node-name;
                tailf:cli-no-value-on-delete;
                type enumeration {
                 enum "application_assurance";
                 enum "aps";
                 enum "atm";
                 enum "bgp";
                 enum "cflowd";
                 enum "chassis";
                  enum "debug";
                  enum "dhcp";
                  enum "dhcps";
                  enum "diameter";
                  enum "dynsvc";
                  enum "efm_oam";
                  enum "elmi";
                  enum "ering";
                  enum "eth_cfm";
                  enum "etun";
                  enum "filter";
                  enum "gsmp";
                  enum "gmpls";
                  enum "igh";
                  enum "igmp";
                  enum "igmp_snooping";
                  enum "ip";
                  enum "ipsec";
                  enum "isis";
                  enum "l2tp";
                  enum "lag";
                  enum "ldp";
                  enum "li";
                  enum "lldp";
                  enum "lmp";
                  enum "logger";
                  enum "mcpath";
                  enum "mc_redundancy";
                  enum "mirror";
                  enum "mld";
                  enum "mld_snooping";
                  enum "mpls";
                  enum "mpls_tp";
                  enum "msdp";
                  enum "nat";
                  enum "ntp";
                  enum "oam";
                  enum "open_flow";
                  enum "ospf";
                  enum "pim";
                  enum "pim_snooping";
                  enum "port";
                  enum "ppp";
                  enum "pppoe";
                  enum "radius";
                  enum "rip";
                  enum "rip_ng";
                  enum "route_policy";
                  enum "rsvp";
                  enum "security";
                  enum "snmp";
                  enum "stp";
                  enum "svcmgr";
                  enum "system";
                  enum "user";
                  enum "video";
                  enum "vrrp";
                  enum "vrtr";
                  enum "wlan_gw";
                  enum "wpp";
                }
              }
            }
            // log / filter * / entry * / match * / message
            container message {
              tailf:info "Specify pattern to match message";
              tailf:cli-compact-syntax;
              tailf:cli-sequence-commands;
              tailf:cli-embed-no-on-delete;
              // log / filter * / entry * / match * / message rule
              leaf rule {
                tailf:cli-drop-node-name;
                tailf:cli-no-value-on-delete;
                type enumeration {
                  enum eq;
                  enum neq;
                }
              }
              // log / filter * / entry * / match * / message pattern
              leaf pattern {
                tailf:cli-no-value-on-delete;
                type string;
              }
              // log / filter * / entry * / match * / message regexp
              leaf regexp {
                tailf:cli-no-name-on-delete;
                type empty;
              }
            }
            // log / filter * / entry * / match * / number
            container number {
              tailf:info "Specify event-id number to match";
              tailf:cli-compact-syntax;
              tailf:cli-sequence-commands;
              tailf:cli-embed-no-on-delete;
              // log / filter * / entry * / match * / number rule
              leaf rule {
                tailf:cli-drop-node-name;
                tailf:cli-no-value-on-delete;
                type enumeration {
                  enum eq;
                  enum neq;
                  enum lt;
                  enum lte;
                  enum gt;
                  enum gte;
                }
              }
              // log / filter * / entry * / match * / number event-id
              leaf event-id {
                tailf:cli-drop-node-name;
                tailf:cli-no-value-on-delete;
                type uint32;
              }
            }
            container router {
              tailf:info "Specify router context string to match";
              tailf:cli-compact-syntax;
              tailf:cli-sequence-commands;
              tailf:cli-embed-no-on-delete;
              // log / filter * / entry * / match * / router rule
              leaf rule {
                tailf:cli-drop-node-name;
                tailf:cli-no-value-on-delete;
                type enumeration {
                  enum eq;
                  enum neq;
                }
              }
              // log / filter * / entry * / match * / router router-instance
              leaf router-instance {
                tailf:cli-drop-node-name;
                tailf:cli-no-value-on-delete;
                type string;
              }
              // log / filter * / entry * / match * / router regexp
              leaf regexp {
                tailf:cli-no-name-on-delete;
                type empty;
              }
            }
            // log / filter * / entry * / match * / severity
            container severity {
              tailf:info "Specify severity level to match";
              tailf:cli-compact-syntax;
              tailf:cli-sequence-commands;
              tailf:cli-embed-no-on-delete;
              // log / filter * / entry * / match * / severity rule
              leaf rule {
                tailf:cli-drop-node-name;
                tailf:cli-no-value-on-delete;
                type enumeration {
                  enum eq;
                  enum neq;
                  enum lt;
                  enum lte;
                  enum gt;
                  enum *;
                }
              }
              // log / filter * / entry * / match * / severity severity-level
              leaf severity-level {
                tailf:cli-drop-node-name;
                tailf:cli-no-value-on-delete;
                type enumeration {
                  enum cleared;
                  enum indeterminate;
                  enum critical;
                  enum major;
                  enum minor;
                  enum warning;
                }
              }
            }
            // log / filter * / entry * / match * / subject
            container subject {
              tailf:info "Specify subject string to match";
              tailf:cli-compact-syntax;
              tailf:cli-sequence-commands;
              tailf:cli-embed-no-on-delete;
              // log / filter * / entry * / match * / router rule
              leaf rule {
                tailf:cli-drop-node-name;
                tailf:cli-no-value-on-delete;
                type enumeration {
                  enum eq;
                  enum neq;
                }
              }
              // log / filter * / entry * / match * / subject subject
              leaf subject {
                tailf:cli-drop-node-name;
                tailf:cli-no-value-on-delete;
                type string;
              }
              // log / filter * / entry * / match * / router regexp
              leaf regexp {
                tailf:cli-no-name-on-delete;
                type empty;
              }
            }
          }
        }
      }


    // log / snmp-trap-group *
    list  snmp-trap-group {
      key id;

      leaf id {
        type uint16;
      }

      // log / snmp-trap-group * / trap-target
      leaf-list trap-target {
        tailf:cli-flat-list-syntax;
        tailf:cli-no-value-on-delete;
        type string;
      }

      // log / snmp-trap-group * / description
      leaf description {
        tailf:cli-embed-no-on-delete;
        tailf:cli-no-value-on-delete;
        type string;
      }
    }

    // log / log-id * /
    list log-id {
      key id;

      leaf id {
        type uint16;
      }

      // log / log-id * / description
      leaf description {
        tailf:cli-no-value-on-delete;
        type string;
      }

      // log / log-id * / filter
      leaf filter {
        tailf:cli-no-value-on-delete;
        tailf:non-strict-leafref {
          path "../../filter/filter-id";
        }
        type uint16;
      }

      // log / log-id * / from
      leaf-list from {
        tailf:cli-flat-list-syntax;
        tailf:cli-no-value-on-delete;
        type string;
      }

      // log / log-id * / time-format
      leaf time-format {
        tailf:cli-no-value-on-delete;
        type string;
      }

      // log / log-id * / to
      container to {
        choice choice {
          case file {
            leaf file {
              type uint32;
            }
          }
          case syslog {
            leaf syslog {
              tailf:non-strict-leafref {
                path "/alu:log/syslog/id";
              }
              type uint32;
            }
          }
          case console {
            leaf console {
              type empty;
            }
          }
          case snmp {
            container snmp {
              presence true;
              leaf size {
                tailf:cli-drop-node-name;
                type uint32;
              }
            }
          }
          case memory {
            leaf memory {
              type empty;
            }
          }
          case session {
            leaf session {
              type uint32;
            }
          }
        }
      }

      // log / log-id * / shutdown
      leaf shutdown {
        tailf:cli-boolean-no;
        default false;
        type boolean;
      }
    }

    // log / syslog *
    list syslog {
      key id;

      leaf id {
        type uint32;
      }

      // log / syslog * / address
      leaf address {
        tailf:cli-no-value-on-delete;
        type union {
          type inet:ipv4-address;
          type inet:ipv6-address;
        }
      }

      // log / syslog * / description
      leaf description {
        tailf:cli-no-value-on-delete;
        type string;
      }

      // log / syslog * / facility
      leaf facility {
        tailf:cli-no-value-on-delete;
        type string;
      }

      // log / syslog * / log-prefix
      leaf log-prefix {
        tailf:cli-no-value-on-delete;
        type string;
      }

      // log / syslog * / level
      leaf level {
        type enumeration {
          enum emergency;
          enum alert;
          enum critical;
          enum error;
          enum warning;
          enum notice;
          enum info;
          enum debug;
        }
      }
    }
  }


  /// ========================================================================
  /// service /
  /// ========================================================================
  container service {
    tailf:info "Services configuration";
    tailf:cli-diff-dependency "/alu:port/shutdown" {
      tailf:cli-trigger-on-all;
    }
    tailf:cli-add-mode;

    // service / customer
    list customer {
      tailf:info "Provision a customer";
      tailf:cli-recursive-delete;
      tailf:cli-embed-no-on-delete;
      key customer-id;
      leaf customer-id {
        type uint32 {
          tailf:info "<customer-id>;;[1..2147483647]";
          range "1 .. 2147483647";
        }
      }

      // service / customer * / create
      leaf create {
        mandatory true;
        type empty;
        tailf:cli-hide-in-submode;
        tailf:cli-no-name-on-delete;
      }

      // service / customer * / contact
      leaf contact {
        tailf:cli-embed-no-on-delete;
        tailf:cli-no-value-on-delete;
        type string;
      }

      // service / customer * / description
      leaf description {
        tailf:cli-embed-no-on-delete;
        tailf:cli-no-value-on-delete;
        type string;
      }

      // service / customer * / multi-service-site
      list multi-service-site {
        tailf:cli-embed-no-on-delete;
        tailf:cli-diff-dependency "/alu:lag";
        tailf:cli-diff-dependency "/alu:port";
        key customer-site-name;
        leaf customer-site-name {
          type string;
        }

        // service / customer * / multi-service-site * / create
        leaf create {
          mandatory true;
          type empty;
          tailf:cli-hide-in-submode;
          tailf:cli-no-name-on-delete;
        }

        // service / customer * / multi-service-site * / assignment
        container assignment {
          tailf:cli-embed-no-on-delete;

          choice choice {
            leaf port {
              tailf:cli-no-name-on-delete;
              tailf:cli-no-value-on-delete;
              tailf:non-strict-leafref {
                path "/alu:port/port-id";
              }
              type string;
            }
            leaf card {
              tailf:cli-no-name-on-delete;
              tailf:cli-no-value-on-delete;
              tailf:non-strict-leafref {
                path "/alu:card/slot-number";
              }
              type string;
            }
          }
        }

        // service / customer * / multi-service-site * / description
        leaf description {
          tailf:cli-embed-no-on-delete;
          tailf:cli-no-value-on-delete;
          type string;
        }

        // service / customer * / multi-service-site * / egress
        container egress {
          tailf:cli-add-mode;

          // service / customer * / multi-service-site * /
          // egress agg-rate-limit
          container agg-rate-limit {
            presence present;
            tailf:cli-sequence-commands;
            tailf:cli-compact-syntax;
            tailf:cli-full-no;
            tailf:cli-recursive-delete;
            tailf:cli-embed-no-on-delete;

            // service / customer * / multi-service-site * /
            //egress agg-rate-limit agg-rate
            leaf agg-rate {
              tailf:cli-drop-node-name;
              tailf:cli-delete-container-on-delete;
              mandatory true;
              type string;
            }

            // service / customer * / multi-service-site * /
            //egress agg-rate queue-frame-based-accounting
            leaf queue-frame-based-accounting {
              tailf:cli-hide-in-submode;
              type empty;
            }
          }

          // service / customer * / multi-service-site * / egress
          // policer-control-policy
          leaf policer-control-policy {
            type string;
          }

          // service / customer * / multi-service-site * / egress
          //scheduler-policy
          leaf scheduler-policy {
             tailf:cli-no-value-on-delete;
            tailf:non-strict-leafref {
              path "/alu:qos/scheduler-policy/scheduler-policy-name";
            }
            type string;
          }

          // service / customer * / multi-service-site * / egress
          // scheduler-override
          container scheduler-override {
            tailf:cli-add-mode;

            // service / customer * / multi-service-site * / egress
            // scheduler-override scheduler
            list scheduler {
              tailf:cli-recursive-delete;
              tailf:cli-embed-no-on-delete;
              key scheduler-name;
              leaf scheduler-name {
                type string;
              }

              // service / customer * / multi-service-site * / egress
              // scheduler-override scheduler * / create
              leaf create {
                mandatory true;
                type empty;
                tailf:cli-hide-in-submode;
                tailf:cli-no-name-on-delete;
              }

              // service / customer * / multi-service-site * / egress +
              // scheduler-override scheduler * / rate
              container rate {
                tailf:cli-sequence-commands;
                tailf:cli-compact-syntax;
                tailf:cli-embed-no-on-delete;

                // service / customer * / multi-service-site * / egress +
                // scheduler-override scheduler * / rate pir-rate
                leaf pir-rate {
                  tailf:cli-drop-node-name;
                  tailf:cli-no-value-on-delete;
                  type string;
                }

                // service / customer * / multi-service-site * / egress +
                // scheduler-override scheduler * / rate cir
                leaf cir {
                  tailf:cli-no-name-on-delete;
                  tailf:cli-no-value-on-delete;
                  type string;
                }
              }
            }
          }
        }

        // service / customer * / multi-service-site * / ingress
        container ingress {
          tailf:cli-add-mode;

          // service / customer * / multi-service-site * / ingress / +
          // policer-control-policy
          leaf policer-control-policy {
            type string;
          }

          // service / customer * / multi-service-site * / ingress / +
          // scheduler-policy
          leaf scheduler-policy {
            tailf:cli-no-value-on-delete;
            tailf:non-strict-leafref {
              path "/alu:qos/scheduler-policy/scheduler-policy-name";
            }
            type string;
          }

          // service / customer * / multi-service-site * / ingress / +
          // scheduler-override
          container scheduler-override {
            tailf:cli-add-mode;

            // service / customer * / multi-service-site * / ingress / +
            // scheduler-override scheduler *
            list scheduler {
              tailf:cli-recursive-delete;
              tailf:cli-embed-no-on-delete;
              key scheduler-name;
              leaf scheduler-name {
                type string;
              }

              // service / customer * / multi-service-site * / ingress / +
              // scheduler-override scheduler * / create
              leaf create {
                mandatory true;
                type empty;
                tailf:cli-hide-in-submode;
                tailf:cli-no-name-on-delete;
              }

              // service / customer * / multi-service-site * / ingress / +
              // scheduler-override scheduler * / rate
              container rate {
                presence present;
                tailf:cli-sequence-commands;
                tailf:cli-compact-syntax;
                tailf:cli-embed-no-on-delete;

                // service / customer * / multi-service-site * / ingress / +
                // scheduler-override scheduler * / rate pir-rate
                leaf pir-rate {
                  tailf:cli-drop-node-name;
                   tailf:cli-no-value-on-delete;
                  mandatory true;
                  type string;
                }


                // service / customer * / multi-service-site * / ingress / +
                // scheduler-override scheduler * / rate cir
                leaf cir {
                  tailf:cli-no-name-on-delete;
                  tailf:cli-no-value-on-delete;
                  type string;
                }
              }
            }
          }
        }

        // service / customer * / multi-service-site * / tod-suite
        leaf tod-suite {
          type string;
        }
      }

      // service / customer * / phone
      leaf phone {
        type string;
      }
    }


    // service / sdp *
    list sdp {
      tailf:info "Provision a SDP";
      tailf:cli-embed-no-on-delete;
      key sdp-id;
      leaf sdp-id {
        type uint32 {
          range "1 .. 17407";
          tailf:info "<sdp-id>;;[1..17407]";
        }
      }

      // service / sdp * / accounting-policy
      leaf accounting-policy {
        tailf:info "Configure accounting-policy to be used";
        tailf:cli-no-value-on-delete;
        type uint8 {
          range "1..99";
        }
      }

      // service / sdp * / adv-mtu-override
      leaf adv-mtu-override {
        tailf:info "Override the advertised VC MTU";
        tailf:cli-no-value-on-delete;
        type empty;
      }

      // service / sdp * / bgp-tunnel
      leaf bgp-tunnel  {
        tailf:info "Enable/disable BGP tunnels";
        type empty;
      }

      // service / sdp * / binding
      container binding {
        tailf:info "Configure binding information";
        tailf:cli-add-mode;

        // service / sdp * / binding / port
        leaf port {
          tailf:info "port;; <port-id | lag-id>";
          tailf:cli-no-value-on-delete;
          type string;
        }

        // service / sdp * / binding / port *
        list pw-port {
          tailf:info "Configure pseudo-wire port information";
          tailf:cli-embed-no-on-delete;
          key pw-port-id;

          leaf pw-port-id {
            tailf:info "<pw-port-id>;;<1..10239>";
            type uint32 {
              range "1..10239";
            }
          }

          // service / sdp * / binding / port * vc-id
          leaf vc-id {
            tailf:info "<vc-id>;;<1..4294967295>";
            tailf:cli-hide-in-submode;
            type uint32 {
              range "1..4294967295";
            }
          }

          // service / sdp * / binding port * create
          leaf create {
            tailf:cli-hide-in-submode;
            tailf:cli-no-name-on-delete;
            mandatory true;
            type empty;
          }

          // service / sdp * / binding port * / egress
          container egress {
            tailf:info "Configure pseudo-wire port egress side parameters";

            // service / sdp * / binding port * / egress shaping
            container shaping {
              tailf:cli-embed-no-on-delete;

              choice choice {
                // service / sdp * / binding port * / egress shaping vport
                leaf vport {
                  tailf:info "<vport-name>";
                  tailf:cli-no-value-on-delete;
                  type string;
                }

                leaf int-dest-id {
                  // service / sdp * / binding port * / egress shaping +
                  // int-dest-id
                  tailf:info " <int-dest-id>";
                  tailf:cli-no-value-on-delete;
                  type string;
                }
              }
            }
          }

          // service / sdp * / binding port * / vc-type
          leaf vc-type {
            tailf:info "<vc-type>;;<ether|vlan>";
            tailf:cli-no-value-on-delete;
            type enumeration {
              enum ether;
              enum vlan;
            }
          }

          // service / sdp * / binding port * / vlan-vc-type
          leaf vlan-vc-tag {
            tailf:info "<vlan-id>;;<0..4094>";
            tailf:cli-no-value-on-delete;
            type uint16 {
              range "0..4094";
            }
          }

          // service / sdp * / binding port * / shutdown
          leaf shutdown {
            tailf:info "Enable/Disable pseudo-wire port";
            tailf:cli-boolean-no;
            default true;
            type boolean;
          }
        }
      }

      // service / sdp * / booking-factor
      leaf booking-factor {
        tailf:info "Configure the SDP booking-factor";
        tailf:cli-no-value-on-delete;
        type uint16 {
          range "0..1000";
        }
      }


      // service / sdp * / collect-stats
      leaf collect-stats {
        tailf:info "Enable/disable statistics collection";
        tailf:cli-no-value-on-delete;
        type empty;
      }

      // service / sdp * / delivery-type
      leaf delivery-type {
        tailf:cli-hide-in-submode;
        tailf:cli-drop-node-name;
        tailf:cli-no-name-on-delete;
        tailf:cli-no-value-on-delete;
        type enumeration {
          enum gre;
          enum mpls;
          enum l2tpv3;
        }
      }

      // service / sdp * / description
      leaf description {
        tailf:cli-no-value-on-delete;
        type string;
      }

      // service / sdp * / create
      leaf create {
        mandatory true;
        type empty;
        tailf:cli-hide-in-submode;
        tailf:cli-no-name-on-delete;
      }

      // service / sdp * / far-end
      leaf far-end {
        tailf:cli-no-value-on-delete;
        type union {
          type inet:ipv4-address;
          type inet:ipv6-address;
        }
      }

      // service / sdp * / keep-alive
      container keep-alive {
        tailf:info "Configure keep alive parameters";
        tailf:cli-add-mode;

        // service / sdp * / keep-alive / hello-time
        leaf hello-time {
          tailf:info "Configure keep-alive hello time";
          tailf:cli-no-value-on-delete;
          type uint16 {
            range "1..3600";
          }
        }

        // service / sdp * / keep-alive / hold-down-time
        leaf hold-down-time {
          tailf:info "Configure keep-alive hold down time";
          tailf:cli-no-value-on-delete;
          type uint16 {
            range "1..3600";
          }
        }

        // service / sdp * / keep-alive / max-drop-count
        leaf max-drop-count {
          tailf:info "Configure keep-alive max-drop-count";
          tailf:cli-no-value-on-delete;
          type uint8 {
            range "1..5";
          }
        }

        // service / sdp * / keep-alive / message-length
        leaf message-length {
          tailf:info "Configure keep-alive message-length";
          tailf:cli-no-value-on-delete;
          type uint16 {
            range "40..9198";
          }
        }

        // service / sdp * / keep-alive / timeout
        leaf timeout {
          tailf:info "Configure keep-alive hello timeout";
          tailf:cli-no-value-on-delete;
          type uint8 {
            range "1..10";
          }
        }

        // service / sdp * / keep-alive / shutdown
        leaf shutdown {
          tailf:info "Enable/disable keep-alive";
          tailf:cli-boolean-no;
          default true;
          type boolean;
        }
      }

      // service / sdp * / ldp
      leaf ldp {
        tailf:info "Enable/disable LDP-signaled LSP's";
        type empty;
      }

      // service / sdp * / lsp
      leaf lsp {
        tailf:info "Configure LSP to be used by SDP";
        tailf:cli-no-value-on-delete;
        tailf:cli-diff-dependency "/alu:router/mpls/lsp";
        tailf:cli-diff-dependency "/alu:router/mpls/static-lsp";
        tailf:non-strict-leafref {
          path "/alu:router/mpls/lsp/name";
        }
        type string;
      }

      // service / sdp * / class-forwarding
      container class-forwarding {
        tailf:info "Configure class-based forwarding";
        tailf:cli-embed-no-on-delete;
        tailf:cli-add-mode;

        // service / sdp * / class-forwarding default-lsp
        leaf default-lsp {
          tailf:info "<default-lsp;;<lsp-name>";
          tailf:cli-hide-in-submode;
          tailf:cli-no-name-on-delete;
          tailf:cli-no-value-on-delete;
          type string;
        }

        // service / sdp * / class-forwarding enforce-diffserv-lsp-fc
        leaf enforce-diffserv-lsp-fc {
          tailf:info "Configure validation of support of fc by lsp with RSVP";
          type empty;
        }

        // service / sdp * / class-forwarding fc
        leaf fc {
          tailf:info "Configure a forwarding class to LSP mapping";
          tailf:cli-no-value-on-delete;
          type enumeration {
            enum be;
            enum l2;
            enum af;
            enum l1;
            enum h2;
            enum ef;
            enum h1;
            enum nc;
          }
        }

        // service / sdp * / class-forwarding multicast-lsp
        leaf multicast-lsp {
          tailf:info "Configure an LSP for all MC traffic";
          tailf:cli-no-value-on-delete;
          type string;
        }

        // service / sdp * / class-forwarding shutdown
        leaf shutdown {
          tailf:info "Administratively enable/disable class-based forwarding";
          tailf:cli-boolean-no;
          default true;
          type boolean;
        }
      }


      // service / sdp * / metric
      leaf metric {
        tailf:info "Configure SDP Metric";
        tailf:cli-no-value-on-delete;
        type uint16 {
          range "1..65535";
        }
      }

      // service / sdp * / mixed-lsp-mode
      container mixed-lsp-mode {
        tailf:info "Enable/disable Mixed LSP mode";
        tailf:cli-embed-no-on-delete;
        tailf:cli-add-mode;

        // service / sdp * / mixed-lsp-mode / revert-time
        leaf revert-time {
          tailf:info "Configure the time to wait before reverting";
          tailf:cli-no-value-on-delete;
          type union {
            type uint16 {
              range "0..600";
            }
            type enumeration {
              enum infinite;
            }
          }
        }
      }

      // service / sdp * / network-domain
      leaf network-domain {
        tailf:info "Configure network-domain";
        tailf:cli-no-value-on-delete;
        type string;
      }

      // service / sdp * / path-mtu
      leaf path-mtu {
        tailf:info "Configure path MTU";
        tailf:cli-no-value-on-delete;
        type uint16 {
          range "576..9194";
        }
      }

      // service / sdp * / pbb-etype
      leaf pbb-etype {
        tailf:info "Configure PBB ethertype";
        tailf:cli-no-value-on-delete;
        type uint16 {
          range "1536..65535";
        }
      }

      // service / sdp * / signaling
      leaf signaling {
        tailf:info "Configure type of VC label signaling";
        tailf:cli-no-value-on-delete;
        type enumeration {
          enum off;
          enum tldp;
          enum bgp;
        }
      }

      // service / sdp * / local-end
      // FIXME; available?
      leaf local-end {
        tailf:cli-no-value-on-delete;
        type inet:ipv6-address;
      }

      // service / sdp * / tunnel-far-end
      leaf tunnel-far-end {
        tailf:info "Configure tunnel-far-end address";
        tailf:cli-no-value-on-delete;
        type inet:ipv4-address;
      }

      // service / sdp * / vlan-vc-type
      leaf vlan-vc-etype {
        tailf:info "Configure VLAN VC ethertype";
        tailf:cli-no-value-on-delete;
        type uint32;
      }

      // service / sdp * / shutdown
      leaf shutdown {
        tailf:info "Administratively enable/disable the SDP";
        tailf:cli-boolean-no;
        default true;
        type boolean;
      }
    }

    // service / epipe *
    list epipe {
      tailf:info "Provision an Ether-Pipe Service";
      tailf:cli-recursive-delete;
      tailf:cli-embed-no-on-delete;
      // Dependency between sap ids and port/lag names.
      tailf:cli-diff-dependency "/alu:port";
      tailf:cli-diff-dependency "/alu:lag";
      key service-id;
      leaf service-id {
        type uint32 {
          range "1 .. 2147483650";
          tailf:info "<service-id>;;[1..2147483650]";
        }
      }

      // service / epipe * / customer
      leaf customer {
        tailf:cli-hide-in-submode;
        tailf:cli-no-name-on-delete;
        tailf:cli-no-value-on-delete;
        type leafref {
          path "/alu:service/customer/customer-id";
        }
      }



      // service / epipe * / description
      leaf description {
        tailf:cli-embed-no-on-delete;
        tailf:cli-no-value-on-delete;
        type string;
      }

      // service / epipe * / vc-switching
      leaf vc-switching {
        tailf:cli-hide-in-submode;
        tailf:cli-no-name-on-delete;
        type empty;
      }

      // service / epipe * / create
      leaf create {
        mandatory true;
        type empty;
        tailf:cli-hide-in-submode;
        tailf:cli-no-name-on-delete;
      }

      // service / epipe * / sap *
      list sap {
        tailf:info "Provision a SAP";
        tailf:cli-embed-no-on-delete;
        tailf:cli-diff-dependency "/alu:service/epipe/endpoint";
        tailf:cli-diff-dependency "/alu:port";
        key sap-id;

        leaf sap-id {
          tailf:cli-diff-dependency "/alu:service/ies/interface/sap"
            + "[sap-id=current()/../sap-id]" {
            tailf:cli-trigger-on-set;
          }
          tailf:cli-diff-dependency "/alu:service/vpls/sap"
            + "[sap-id=current()/../sap-id]" {
            tailf:cli-trigger-on-set;
          }
          tailf:cli-diff-dependency "/alu:service/vprn/interface/sap"
            + "[sap-id=current()/../sap-id]" {
            tailf:cli-trigger-on-set;
          }
          tailf:cli-diff-dependency "/alu:service/epipe/sap"
            + "[sap-id=current()/../sap-id]" {
            tailf:cli-trigger-on-set;
          }
          tailf:info "<sap-id>;;different formats depending on port mode";
          type string;
        }

        // service / epipe * / sap * endpoint
        leaf endpoint {
          tailf:cli-hide-in-submode;
          tailf:cli-no-name-on-delete;
          tailf:cli-no-value-on-delete;
          type leafref {
            path "/alu:service/epipe/endpoint/endpoint-name";
          }
        }

        // service / epipe * / sap * / egress
        container egress {
          tailf:cli-add-mode;

          // service / epipe * / sap  * / egress qos
          leaf qos {
            tailf:info "Apply egress qos policy";
            type uint16;
            tailf:non-strict-leafref {
              path "/alu:qos/sap-egress/policy-id";
            }
          }
        }

        // service / epipe * / sap * / ingress
        container ingress {
          tailf:cli-add-mode;

          // service / epipe * / sap * / ingress qos
          leaf qos {
            tailf:info "Apply ingress qos policy";
            type uint16;
            tailf:non-strict-leafref {
              path "/alu:qos/sap-ingress/policy-id";
            }
          }
        }

        // service / epipe * / sap * / description
        leaf description {
          tailf:info "Description for the SAP";
          tailf:cli-embed-no-on-delete;
          tailf:cli-no-value-on-delete;
          type string;
        }

        // service / epipe * / sap * / eth-cfm
        container eth-cfm {
          tailf:cli-add-mode;
          uses eth-cfm;
        }

        // service / epipe * / sap * / multi-service-site
        leaf multi-service-site {
          tailf:cli-no-value-on-delete;
          type leafref {
            path "/alu:service/customer/multi-service-site/customer-site-name";
          }
        }

        // service / epipe * / sap * / oper-group
        leaf oper-group {
          tailf:info "Configure operational-group";
          tailf:cli-embed-no-on-delete;
          tailf:cli-no-value-on-delete;
          tailf:non-strict-leafref {
            path "/alu:service/oper-group/group-name";
          }
          type string;
        }

        // service / epipe * / sap * / shutdown
        leaf shutdown {
          type empty;
        }

        // service / epipe * / sap * / create
        leaf create {
          type empty;
          mandatory true;
          tailf:cli-hide-in-submode;
          tailf:cli-no-name-on-delete;
        }
      }

      // service / epipe * / service-name
      leaf service-name {
        tailf:info "Configure a service name";
        tailf:cli-embed-no-on-delete;
        tailf:cli-no-value-on-delete;
        type string;
      }

      // service / epipe * / service-mtu
      leaf service-mtu {
        tailf:info "Configure service MTU";
        tailf:cli-embed-no-on-delete;
        tailf:cli-no-value-on-delete;
        type uint16 {
          range "1..9194";
        }
      }

      // service / epipe * / site *
      list site {
        tailf:cli-embed-no-on-delete;
        tailf:cli-recursive-delete;
        key name;

        leaf name {
          type string {
            length "1..32";
          }
        }

        // service / epipe * / site * / boot-timer
        leaf boot-timer {
          tailf:info "Configure/Override site boot-timer";
          tailf:cli-embed-no-on-delete;
          tailf:cli-no-value-on-delete;
          type uint16 {
            range "0..600";
          }
        }

        // service / epipe * / site * / sap
        leaf sap {
          tailf:info
            tailf:cli-embed-no-on-delete;
          tailf:cli-no-value-on-delete;
          type string;
        }

        // service / epipe * / site * / site-activation-timer
        leaf site-activation-timer {
          tailf:info "Configure/Override site activation timer";
          tailf:cli-embed-no-on-delete;
          tailf:cli-no-value-on-delete;
          type uint16 {
            range "0..100";
          }
        }

        // service / epipe * / site * / site-id
        leaf site-id {
          tailf:info "Configure site identifier";
          tailf:cli-embed-no-on-delete;
          tailf:cli-no-value-on-delete;
          type uint16;
        }

        // service / epipe * / site * / shutdown
        leaf shutdown {
          tailf:info "Administratively enable/disable the site";
          tailf:cli-boolean-no;
          default true;
          type boolean;
        }
        // service / epipe * / site * / create
        leaf create {
          type empty;
          mandatory true;
          tailf:cli-hide-in-submode;
          tailf:cli-no-name-on-delete;
        }
      }

      // service / epipe * / spoke-sdp *
      list spoke-sdp {
        tailf:info "<sdp-id>:<vc-id>";
        //tailf:cli-recursive-delete;
        tailf:cli-embed-no-on-delete;
        tailf:cli-key-format "$(1):$(2)";
        uses sdp-common;
        key "sdp-id vc-id";

        // service / epipe * / spoke-sdp * / egress
        container egress {
          tailf:cli-add-mode;
          tailf:cli-no-name-on-delete;

          // service / epipe * / spoke-sdp * / egress l2tpv3
          container l2tpv3 {
            tailf:cli-add-mode;
            tailf:cli-no-name-on-delete;

            // service / epipe * / spoke-sdp * / egress l2tpv3 cookie
            leaf cookie {
              tailf:cli-no-name-on-delete;
              tailf:cli-no-value-on-delete;
              type string;
            }
          }
        }

        // service / epipe * / spoke-sdp * / ingress
        container ingress {
          tailf:cli-add-mode;
          tailf:cli-no-name-on-delete;

          // service / epipe * / spoke-sdp * / ingress l2tpv3
          container l2tpv3 {
            tailf:cli-add-mode;
            tailf:cli-no-name-on-delete;

            // service / epipe * / spoke-sdp * / ingress l2tpv3 cookie
            leaf cookie {
              tailf:cli-no-name-on-delete;
              tailf:cli-no-value-on-delete;
              type string;
            }
          }
        }

        // service / epipe * / spoke-sdp * / pw-status-signalling
        leaf pw-status-signaling {
          type empty;
        }

        leaf control-word {
          tailf:info "Enable/disable setting the CW bit in the label message";
          tailf:cli-embed-no-on-delete;
          type empty;
        }

        // service / epipe * / spoke-sdp * / precedence
        leaf precedence {
          tailf:info "Configure the spoke-sdp precedence";
          tailf:cli-embed-no-on-delete;
          tailf:cli-no-value-on-delete;
          type union {
            type enumeration {
              enum primary;
            }
            type uint8 {
              range "1..4";
            }
          }
        }
      }

      // service / epipe * / endpoint *
      list endpoint {
        tailf:info "Configure a service end-point";
        tailf:cli-embed-no-on-delete;
        //tailf:cli-recursive-delete;
        key endpoint-name;

        leaf endpoint-name {
          type string;
        }

        // service / epipe * / endpoint * create
        leaf create {
          tailf:cli-hide-in-submode;
          tailf:cli-no-name-on-delete;
          mandatory true;
          type empty;
        }

        // service / epipe * / endpoint * / active-hold-delay
        leaf active-hold-delay {
          tailf:info "Configure the time to hold the active status";
          tailf:cli-embed-no-on-delete;
          tailf:cli-no-value-on-delete;
          type uint8 {
            range "1..60";
          }
        }

        // service / epipe * / endpoint * / description
        leaf description  {
          tailf:info "Description for the service end-point";
          tailf:cli-embed-no-on-delete;
          tailf:cli-no-value-on-delete;
          type string;
        }

        // service / epipe * / endpoint * / revert-time
        leaf revert-time {
          tailf:info "Configure the time to wait before reverting to primary";
          tailf:cli-embed-no-on-delete;
          tailf:cli-no-value-on-delete;
          type union {
            type enumeration {
              enum infinite;
            }
            type uint16 {
              range "0..600";
            }
          }
        }

        // service / epipe * / endpoint * / standby-signaling-master
        leaf standby-signaling-master {
          tailf:info "Enable PW standby-signaling master";
          tailf:cli-no-value-on-delete;
          type empty;
        }

        // service / epipe * / endpoint * / signaling-master
        leaf standby-signaling-slave {
          tailf:info "Enable PW standby-signaling master";
          tailf:cli-no-value-on-delete;
          type empty;
        }
      }

      // service / epipe * / shutdown
      leaf shutdown {
        tailf:cli-boolean-no;
        default true;
        type boolean;
      }
    }


    // service / oper-group *
    list oper-group {
      tailf:info "Configure a Operational-Group information";
      key group-name;

      leaf group-name {
        tailf:cli-embed-no-on-delete;
        type string;
      }

      // service / oper-group * / hold-time
      container hold-time {
        tailf:info "Configure hold-time information";
        tailf:cli-add-mode;

        // service / oper-group * / hold-time / group
        leaf group {
          tailf:info "Configure group up/down time information";
          tailf:cli-embed-no-on-delete;
          type empty;
        }
      }

      // service / oper-group * / create
      leaf create {
        tailf:cli-hide-in-submode;
        tailf:cli-no-name-on-delete;
        mandatory true;
        type empty;
      }
    }

    // service / ies *
    list ies {
      tailf:info "Provision an Internet Enhanced Service";
      tailf:cli-recursive-delete;
      tailf:cli-embed-no-on-delete;
      // Dependency between sap ids and port/lag names.
      tailf:cli-diff-dependency "/alu:port";
      tailf:cli-diff-dependency "/alu:lag";

      key service-id;
      leaf service-id {
        type uint32 {
          range "1 .. 2147483650";
          tailf:info "<service-id>;;[1..2147483650]";
        }
      }

      // service / ies * / customer
      leaf customer {
        tailf:cli-hide-in-submode;
        tailf:cli-no-name-on-delete;
        tailf:cli-no-value-on-delete;
        type leafref {
          path "/alu:service/customer/customer-id";
        }
      }

      // service / ies * / create
      leaf create {
        mandatory true;
        type empty;
        tailf:cli-hide-in-submode;
        tailf:cli-no-name-on-delete;
      }

      // service / ies * / description
      leaf description {
        tailf:cli-embed-no-on-delete;
        tailf:cli-no-value-on-delete;
        type string;
      }

      // service / ies * / subscriber-interface *
      list subscriber-interface {
        tailf:cli-recursive-delete;
        tailf:cli-embed-no-on-delete;
        key id;
        leaf id {
          type string;
        }

        // service / ies * / subscriber-interface * / create
        leaf create {
          mandatory true;
          type empty;
          tailf:cli-hide-in-submode;
          tailf:cli-no-name-on-delete;
        }

        // service / ies * / subscriber-interface * / address
        leaf address {
          type tailf:ipv4-address-and-prefix-length;
        }

        // service / ies * / subscriber-interface * / group-interface *
        list group-interface {
          tailf:cli-recursive-delete;
          tailf:cli-embed-no-on-delete;
          key id;
          leaf id {
            type string;
          }

          // service / ies * / subscriber-interface * / group-interface * / +
          // create
          leaf create {
            mandatory true;
            type empty;
            tailf:cli-hide-in-submode;
            tailf:cli-no-name-on-delete;
          }

          // service / ies * / subscriber-interface * / group-interface * / +
          // description
          leaf description {
            tailf:cli-no-value-on-delete;
            type string;
          }

          // service / ies * / subscriber-interface * / group-interface * /
          //icmp
          container icmp {
            tailf:cli-add-mode;

            // service / ies * / subscriber-interface * / group-interface * /
            // icmp mask-reply
            leaf mask-reply {
              type boolean;
              tailf:cli-boolean-no;
            }

            // service / ies * / subscriber-interface * / group-interface * / +
            // icmp redirects
            container redirects {
              tailf:cli-compact-syntax;
              tailf:cli-sequence-commands {
                tailf:cli-reset-siblings;
              }

              // service / ies * / subscriber-interface * / group-interface * /
              // icmp redirects number
              leaf number {
                tailf:cli-drop-node-name;
                tailf:cli-no-value-on-delete;
                type uint16 {
                  range "10..1000";
                }
              }

              // service / ies * / subscriber-interface * / group-interface * /
              // icmp redirects seconds
              leaf seconds {
                tailf:cli-drop-node-name;
                tailf:cli-no-value-on-delete;
                type uint8 {
                  range "1..60";
                }
              }
            }

            // service / ies * / subscriber-interface * / group-interface * /
            // icmp unreachables
            container unreachables {
              tailf:cli-compact-syntax;
              tailf:cli-sequence-commands {
                tailf:cli-reset-siblings;
              }

              // service / ies * / subscriber-interface * / group-interface * /
              // icmp unreachables number
              leaf number {
                tailf:cli-drop-node-name;
                tailf:cli-no-value-on-delete;
                type uint16 {
                  range "10..1000";
                }
              }

              // service / ies * / subscriber-interface * / group-interface * /
              // icmp unreachables seconds
              leaf seconds {
                tailf:cli-drop-node-name;
                tailf:cli-no-value-on-delete;
                type uint8 {
                  range "1..60";
                }
              }
            }

            // service / ies * / subscriber-interface * / group-interface * /
            // icmp ttl-expired
            container ttl-expired {
              tailf:cli-compact-syntax;
              tailf:cli-sequence-commands {
                tailf:cli-reset-siblings;
              }

              // service / ies * / subscriber-interface * / group-interface * /
              // icmp ttl-expired number
              leaf number {
                tailf:cli-drop-node-name;
                tailf:cli-no-value-on-delete;
                type uint16 {
                  range "10..1000";
                }
              }

              // service / ies * / subscriber-interface * / group-interface * /
              // icmp ttl-expired seconds
              leaf seconds {
                tailf:cli-drop-node-name;
                tailf:cli-no-value-on-delete;
                type uint8 {
                  range "1..60";
                }
              }
            }
          }

          // service / ies * / subscriber-interface * / group-interface * /
          // ipv6
          container ipv6 {
            tailf:cli-add-mode;

            // service / ies * / subscriber-interface * / group-interface * /
            // ipv6 / router-advertisements
            container router-advertisements {
              tailf:cli-add-mode;

              // service / ies * / subscriber-interface * / group-interface * /
              // ipv6 / router-advertisements / managed-configuration
              leaf managed-configuration {
                type empty;
              }

              // service / ies * / subscriber-interface * / group-interface * /
              // ipv6 / router-advertisements / shutdown
              leaf shutdown {
                tailf:cli-boolean-no;
                default true;
                type boolean;
              }
            }

            // service / ies * / subscriber-interface * / group-interface * /
            // ipv6 / dhcp6
            container dhcp6 {
              tailf:cli-add-mode;

              // service / ies * / subscriber-interface * / group-interface * /
              // ipv6 / dhcp6 / proxy-server
              container proxy-server {
                tailf:cli-add-mode;

                // service / ies * / subscriber-interface * /
                // group-interface * / ipv6 / dhcp6 / proxy-server / lease-time
                container lease-time {
                  tailf:cli-compact-syntax;

                  // service / ies * / subscriber-interface * /
                  // group-interface * / ipv6 / dhcp6 / proxy-server /
                  // lease-time days
                  leaf days {
                    tailf:cli-no-name-on-delete;
                    tailf:cli-no-value-on-delete;
                    type uint16;
                  }

                  // service / ies * / subscriber-interface * /
                  // group-interface * / ipv6 / dhcp6 / proxy-server /
                  // lease-time hrs
                  leaf hrs {
                    tailf:cli-no-name-on-delete;
                    tailf:cli-no-value-on-delete;
                    type uint16;
                  }

                  /// service / ies * / subscriber-interface * /
                  // group-interface * / ipv6 / dhcp6 / proxy-server /
                  // lease-time min
                  leaf min {
                    tailf:cli-no-name-on-delete;
                    tailf:cli-no-value-on-delete;
                    type uint16;
                  }

                  // service / ies * / subscriber-interface * /
                  // group-interface * / ipv6 / dhcp6 / proxy-server /
                  // lease-time sec
                  leaf sec {
                    tailf:cli-no-name-on-delete;
                    tailf:cli-no-value-on-delete;
                    type uint16;
                  }
                }

                // service / ies * / subscriber-interface * /
                // group-interface * / ipv6 / dhcp6 / proxy-server / shutdown
                leaf shutdown {
                  tailf:cli-boolean-no;
                  default true;
                  type boolean;
                }
              }
            }
          }

          // service / ies * / subscriber-interface * / group-interface * / +
          // arp-populate
          leaf arp-populate {
            type empty;
          }

          // service / ies * / subscriber-interface * / group-interface * / +
          // dhcp
          container dhcp {
            tailf:cli-add-mode;

            // service / ies * / subscriber-interface * / group-interface * / +
            // dhcp / proxy-server
            container proxy-server {
              tailf:cli-add-mode;

              // service / ies * / subscriber-interface * / group-interface * /
              // dhcp / proxy-server / lease-time
              container lease-time {
                tailf:cli-compact-syntax;

                // service / ies * / subscriber-interface * / +
                // group-interface * / + dhcp / proxy-server / lease-time days
                leaf days {
                  tailf:cli-no-name-on-delete;
                  tailf:cli-no-value-on-delete;
                  type uint16;
                }

                // service / ies * / subscriber-interface * / +
                // group-interface * / dhcp / proxy-server / lease-time hrs
                leaf hrs {
                  tailf:cli-no-name-on-delete;
                  tailf:cli-no-value-on-delete;
                  type uint16;
                }

                // service / ies * / subscriber-interface * / +
                // group-interface * / dhcp / proxy-server / lease-time min
                leaf min {
                  tailf:cli-no-name-on-delete;
                  tailf:cli-no-value-on-delete;
                  type uint16;
                }

                // service / ies * / subscriber-interface * / +
                // group-interface * / dhcp / proxy-server / lease-time sec
                leaf sec {
                  tailf:cli-no-name-on-delete;
                  tailf:cli-no-value-on-delete;
                  type uint16;
                }
              }

              // service / ies * / subscriber-interface * / +
              // group-interface * / dhcp / proxy-server / shutdown
              leaf shutdown {
                tailf:cli-boolean-no;
                default true;
                type boolean;
              }
            }

            // service / ies * / subscriber-interface * / +
            // group-interface * / dhcp / option
            container option {
              tailf:cli-add-mode;

              // service / ies * / subscriber-interface * / +
              // group-interface * / dhcp / option / action
              leaf action {
                tailf:cli-no-value-on-delete;
                type enumeration {
                  enum replace;
                  enum drop;
                  enum keep;
                }
              }

              // service / ies * / subscriber-interface * / +
              // group-interface * / dhcp / option / circuit-id
              container circuit-id {
                presence true;

                // service / ies * / subscriber-interface * / +
                // group-interface * / dhcp / option / circuit-id id
                leaf id {
                  tailf:cli-drop-node-name;
                  tailf:cli-no-value-on-delete;
                  type enumeration {
                    enum ascii-tuple;
                    enum ifindex;
                    enum sap-id;
                    enum vlan-ascii-tuple;
                  }
                }
              }

              // service / ies * / subscriber-interface * / +
              // group-interface * / dhcp / option / remote-id
              container remote-id {
                presence true;
                choice remote-id {

                  // service / ies * / subscriber-interface * / +
                  // group-interface * / dhcp / option / remote-id mac
                  leaf mac {
                    tailf:cli-drop-node-name;
                    type string;
                    tailf:cli-disallow-value "string";
                  }

                  // service / ies * / subscriber-interface * / +
                  // group-interface * / dhcp / option / remote-id string
                  leaf string {
                    type string;
                  }
                }
              }
            }

            // service / ies * / subscriber-interface * / +
            // group-interface * / dhcp / server
            leaf-list server {
              type inet:ipv4-address;
              tailf:cli-flat-list-syntax;
              tailf:cli-no-value-on-delete;
            }

            // service / ies * / subscriber-interface * / +
            // group-interface * / dhcp / trusted
            leaf trusted {
              type empty;
            }

            // service / ies * / subscriber-interface * / +
            // group-interface * / dhcp / lease-populate
            container lease-populate {
              presence true;
              tailf:cli-compact-syntax;
              tailf:cli-sequence-commands {
                tailf:cli-reset-siblings;
              }

              // service / ies * / subscriber-interface * / +
              // group-interface * / dhcp / lease-populate nr-of-leases
              leaf nr-of-leases {
                tailf:cli-drop-node-name;
                tailf:cli-no-value-on-delete;
                type uint16;
              }

              // service / ies * / subscriber-interface * / +
              // group-interface * / dhcp / lease-populate l2-header
              leaf l2-header {
                tailf:cli-no-name-on-delete;
                type empty;
              }

              // service / ies * / subscriber-interface * / +
              // group-interface * / dhcp / lease-populate mac
              leaf mac {
                tailf:cli-no-name-on-delete;
                tailf:cli-no-value-on-delete;
                type string;
              }
            }

            // service / ies * / subscriber-interface * / +
            // group-interface / dhcp / gi-address
            container gi-address {
              tailf:cli-compact-syntax;
              tailf:cli-sequence-commands {
                tailf:cli-reset-siblings;
              }

              // service / ies * / subscriber-interface * / +
              // group-interface * / dhcp / gi-address address
              leaf address {
                tailf:cli-drop-node-name;
                type inet:ipv4-address;
              }

              // service / ies * / subscriber-interface * / +
              // group-interface * / dhcp / gi-address src-ip-address
              leaf src-ip-address {
                type empty;
              }
            }

            // service / ies * / subscriber-interface * /  +
            // group-interface * / dhcp / shutdown
            leaf shutdown {
              tailf:cli-boolean-no;
              default true;
              type boolean;
            }
          }

          // service / ies * / subscriber-interface * / +
          // group-interface * / sap *
          list sap {
            tailf:cli-recursive-delete;
            tailf:cli-embed-no-on-delete;
            key id;
            leaf id {
              type string;
            }

            // service / ies * / subscriber-interface * / +
            // group-interface * / sap * / create
            leaf create {
              tailf:cli-hide-in-submode;
              tailf:cli-no-name-on-delete;
              mandatory true;
              type empty;
            }

            // service / ies * / subscriber-interface * / +
            // group-interface * / sap * / leaf-description
            leaf description {
              tailf:cli-embed-no-on-delete;
              tailf:cli-no-value-on-delete;
              type string;
            }

            // service / ies * / subscriber-interface * / +
            // group-interface * / sap * / anti-spoof
            leaf anti-spoof {
              tailf:cli-no-value-on-delete;
              type enumeration {
                enum ip;
                enum ip-mac;
                enum nh-mac;
              }
            }

            // service / ies * / subscriber-interface * / +
            // group-interface * / sap * / sub-sla-mgmt
            container sub-sla-mgmt {
              tailf:cli-add-mode;
              tailf:cli-recursive-delete;

              // service / ies * / subscriber-interface * / +
              // group-interface * / sap * / sub-sla-mgmt / def-sub-id
              container def-sub-id {
                choice sub-id-choice {

                  // service / ies * / subscriber-interface * / +
                  // group-interface * / sap * / sub-sla-mgmt / dev-sub-id
                  // string
                  leaf string {
                    tailf:cli-no-value-on-delete;
                    tailf:cli-no-name-on-delete;
                    type string;
                  }

                  // service / ies * / subscriber-interface * / +
                  // group-interface * / sap * / sub-sla-mgmt / dev-sub-id
                  // use-auto-id
                  leaf use-auto-id {
                    tailf:cli-no-name-on-delete;
                    type empty;
                  }

                  // service / ies * / subscriber-interface * / +
                  // group-interface * / sap * / sub-sla-mgmt / dev-sub-id
                  // use-sap-id
                  leaf use-sap-id {
                    tailf:cli-no-name-on-delete;
                    type empty;
                  }
                }
              }

              // service / ies * / subscriber-interface * / +
              // group-interface * / sap * / sub-sla-mgmt / def-sub-profile
              leaf def-sub-profile {
                tailf:cli-no-value-on-delete;
                type string;
              }

              // service / ies * / subscriber-interface * / +
              // group-interface * / sap * / sub-sla-mgmt / def-sla-profile
              leaf def-sla-profile {
                tailf:cli-no-value-on-delete;
                type string;
              }

              // service / ies * / subscriber-interface * / +
              // group-interface * / sap * / sub-sla-mgmt /
              // single-sub-parameters
              container single-sub-parameters {
                tailf:cli-add-mode;
                tailf:cli-no-name-on-delete;
                leaf profiled-traffic-only {
                  type empty;
                }
              }

              // service / ies * / subscriber-interface * / +
              // group-interface * / sap * / sub-sla-mgmt / +
              // single-sub-parameters
              leaf shutdown {
                tailf:cli-boolean-no;
                default true;
                type boolean;
              }
            }

            // service / ies * / subscriber-interface * / +
            // group-interface * / sap * / calling-station-id
            leaf calling-station-id {
              tailf:cli-no-value-on-delete;
              type string;
            }

            // service / ies * / subscriber-interface * /  +
            // group-interface * / sap * / shutdown
            leaf shutdown {
              tailf:cli-boolean-no;
              default true;
              type boolean;
            }
          }
        }
      }

      // service / ies * / interface *
      list interface {
        tailf:cli-recursive-delete;
        tailf:cli-embed-no-on-delete;
        // Dependency between sap ids and port/lag names.
        tailf:cli-diff-dependency "/alu:port";
        tailf:cli-diff-dependency "/alu:lag";
        key ip-int-name;

        leaf ip-int-name {
          type string;
        }

        // service / create
        leaf create {
          tailf:cli-hide-in-submode;
          tailf:cli-no-name-on-delete;
          mandatory true;
          type empty;
        }

        // service / ies * / interface * / address
        leaf address {
          tailf:info "Assigns an IP address to the interface";
          tailf:cli-no-value-on-delete;
          type tailf:ipv4-address-and-prefix-length;
        }

        // service / ies * / interface * / allow-directed-broadcasts
        leaf allow-directed-broadcasts {
          tailf:info "Enable/disable forwarding of directed broadcasts";
          type empty;
        }

        // service / ies * / interface * / arp-populate
        leaf arp-populate {
          tailf:info "Configures the ARP populate option";
          type empty;
        }

        // service / ies * / interface * / arp-timeout
        leaf arp-timeout {
          tailf:info "Configures timeout for an ARP entry learned";
          tailf:cli-no-value-on-delete;
          type uint16;
        }

        // service / ies * / interface * / authentication-policy
        leaf authentication-policy {
          tailf:info "Configures the authentication policy for this interface";
          tailf:cli-no-value-on-delete;
          type string;
        }

        // service / ies * / interface * / bfd
        container bfd {
          tailf:info "Configure BFD parameters";
          tailf:cli-embed-no-on-delete;
          tailf:cli-compact-syntax;
          tailf:cli-sequence-commands;

          leaf transmit-interval {
            tailf:cli-drop-node-name;
            tailf:cli-no-value-on-delete;
            type uint32 {
              range "10..100000";
            }
          }

          leaf receive {
            tailf:cli-no-value-on-delete;
            type uint32 {
              range "10..100000";
            }
          }

          leaf multiplier {
            tailf:cli-no-value-on-delete;
            type uint8 {
              range "3..20";
            }
          }

          leaf echo-receive {
            tailf:cli-no-value-on-delete;
            type uint32 {
              range "100..100000";
            }
          }

          leaf type {
            tailf:cli-no-value-on-delete;
            type enumeration {
              enum cpm-np;
            }
          }
        }

        // service / ies * / interface * / cflowd
        container cflowd {
          tailf:info "Configure Cflowd collection and analysis on this if";
          tailf:cli-embed-no-on-delete;
          tailf:cli-compact-syntax;
          tailf:cli-sequence-commands;

          leaf id {
            tailf:cli-drop-node-name;
            tailf:cli-no-value-on-delete;
            type enumeration {
              enum acl;
              enum interface;
            }
          }

          leaf direction {
            tailf:cli-drop-node-name;
            tailf:cli-no-value-on-delete;
            type enumeration {
              enum ingress-only;
              enum egress-only;
              enum both;
            }
          }
        }

        // service / ies * / interface * / cpu-protection
        leaf cpu-protection {
          tailf:info "Configure a CPU protection policy";
          tailf:cli-no-value-on-delete;
          type uint8 {
            range "1..255";
          }
        }

         // service / ies * /interface * / delayed-enable
        leaf delayed-enable {
          tailf:info "Delays making interface operational";
          tailf:cli-no-value-on-delete;
          type uint16 {
            range "1..1200";
          }
        }

         // service / ies * / interface * / description
         leaf description {
          tailf:info "Description for IES interface";
          tailf:cli-no-value-on-delete;
          type string;
         }

        // service / ies * / interface * / dhcp /
        container dhcp {
          tailf:info "Configure DHCP parameters";
          tailf:cli-add-mode;
        }

         // service / ies * / interface * / dynamic-tunnel-redundant-next-hop
        leaf dynamic-tunnel-redundant-next-hop {
          tailf:info "Configure dynamic ISA tunnel redundant next-hop address";
          tailf:cli-no-value-on-delete;
          type inet:ipv4-address;
        }

        // service / ies * / interface * / enable-ingress-stats
        leaf enable-ingress-stats {
          tailf:info "Enable/disable the gathering of ingress if stats";
          type empty;
        }

        // service / ies * / interface * / enable-mac-accounting
        leaf enable-mac-accounting {
          tailf:info "Configure MAC Accounting functionality for the if";
          type empty;
        }

        // service / ies * / interface * / host-connectivity
        container host-connectivity {
          tailf:info "Enable/disable host connectivity verification";
          tailf:cli-embed-no-on-delete;
          tailf:cli-compact-syntax;
          tailf:cli-sequence-commands;

          leaf source {
            tailf:cli-no-value-on-delete;
            type enumeration {
              enum vrrp;
              enum interface;
            }
          }

          leaf interval {
            tailf:cli-no-value-on-delete;
            type uint16 {
              range "1..6000";
            }
          }

          leaf action {
            tailf:cli-no-value-on-delete;
            type enumeration {
              enum remove;
              enum alarm;
            }
          }

          leaf timeout {
            tailf:cli-no-value-on-delete;
            type uint8 {
              range "10..60";
            }
          }

          leaf count {
            tailf:cli-no-value-on-delete;
            type uint8 {
              range "2..29";
            }
          }
        }

        // service / ies * / interface * / icmp /
        container icmp {
          tailf:info "Configure ICMP parameters for the interface";
          tailf:cli-add-mode;

          // service / ies * / interface * / icmp / mask-reply
          leaf mask-reply {
            tailf:info "Enable/disable responses to ICMP mask requests";
            type empty;
          }

          // service / ies * / interface * / icmp / redirects
          container redirects {
            tailf:info "Configures rate for ICMP redirect messages";
            tailf:cli-embed-no-on-delete;
            tailf:cli-compact-syntax;
            tailf:cli-sequence-commands;

            leaf number {
              tailf:cli-drop-node-name;
              tailf:cli-no-value-on-delete;
              type uint16 {
                range "10..1000";
              }
            }

            leaf seconds {
              tailf:cli-drop-node-name;
              tailf:cli-no-value-on-delete;
              type uint8 {
                range "1..60";
              }
            }
          }

          // service / ies * / interface * / icmp / ttl-expired
          container ttl-expired {
            tailf:info "Configures rate for ICMP TTL expired messages";
            tailf:cli-embed-no-on-delete;
            tailf:cli-compact-syntax;
            tailf:cli-sequence-commands;

            leaf number {
              tailf:cli-drop-node-name;
              tailf:cli-no-value-on-delete;
              type uint16 {
                range "10..1000";
              }
            }

            leaf seconds {
              tailf:cli-drop-node-name;
              tailf:cli-no-value-on-delete;
              type uint8 {
                range "1..60";
              }
            }
          }

          // service / ies * / interface * / icmp / unreachables
          container unreachables {
            tailf:info "Configures rate for ICMP unreachable messages";
            tailf:cli-embed-no-on-delete;
            tailf:cli-compact-syntax;
            tailf:cli-sequence-commands;

            leaf number {
              tailf:cli-drop-node-name;
              tailf:cli-no-value-on-delete;
              type uint16 {
                range "10..1000";
              }
            }

            leaf seconds {
              tailf:cli-drop-node-name;
              tailf:cli-no-value-on-delete;
              type uint8 {
                range "1..60";
              }
            }
          }
    }

        // service / ies * / interface * / ip-mtu
        leaf ip-mtu {
          tailf:info "Configure the interface IP MTU";
          tailf:cli-no-value-on-delete;
          type uint16 {
            range "512..9000";
          }
        }

        // service / ies * / interface * / ipv6
        container ipv6 {
          tailf:cli-add-mode;

          // service / ies * / interface * / ipv6 / address *
          list address {
            tailf:cli-embed-no-on-delete;
            tailf:cli-suppress-mode;
            key "addr";

            leaf addr {
              type tailf:ipv6-address-and-prefix-length;
            }
          }

          // service / ies * / interface * / ipv6 / dhcp6-relay
          container dhcp6-relay {
            tailf:cli-add-mode;
            tailf:cli-embed-no-on-delete;

            // service / ies * / interface * / ipv6 / dhcp6-relay / description
            leaf description {
              tailf:cli-embed-no-on-delete;
              tailf:cli-no-value-on-delete;
              type string;
            }

            // service / ies * / interface * / ipv6 dhcp6-relay / lease-populate
            container lease-populate {
              presence present;
              tailf:cli-sequence-commands;
              tailf:cli-compact-syntax;
              tailf:cli-no-name-on-delete;

              // service / ies * / interface * / ipv6 / dhcp6-relay +
              // lease-populate nbr-of-leases
              leaf nbr-of-leases {
                tailf:cli-drop-node-name;
                tailf:cli-delete-container-on-delete;
                //mandatory true;
                type uint32 {
                  range "1 .. 8000";
                }
              }

              // service / ies * / interface * / ipv6 / dhcp6-relay +
              // lease-populate route-populate
              leaf route-populate {
                tailf:cli-incomplete-command;
                type empty;
              }

              // service / ies * / interface * / ipv6 / dhcp6-relay +
              // lease-populate pd
              leaf pd {
                type empty;
              }

              // service / ies * / interface * / ipv6 / dhcp6-relay +
              // lease-populate exclude
              leaf exclude {
                tailf:cli-break-sequence-commands;
                type empty;
              }

              // service / ies * / interface * / ipv6 dhcp6-relay +
              // lease-populate na
              leaf na {
                //when "../exclude";
                type empty;
              }

              // service / ies * / interface * / ipv6 / dhcp6-relay +
              // lease-populate ta
              leaf ta {
                //when "../exclude";
                type empty;
              }
            }

            // service / ies * / interface * / ipv6 dhcp6-relay +
            // neighbor-resulution
            leaf neighbor-resolution {
              type empty;
            }

            // service / ies * / interface * / ipv6 dhcp6-relay +
            // option
            container option {
              tailf:cli-add-mode;

              // service / ies * / interface * / ipv6 dhcp6-relay +
              // option / interface-id
              container interface-id {
                tailf:cli-embed-no-on-delete;

                // service / ies * / interface * / ipv6 dhcp6-relay +
                // option interface-id sap-id
                choice choice {

                  leaf sap-id {
                    tailf:cli-no-name-on-delete;
                    type empty;
                  }

                  // service / ies * / interface * / ipv6 dhcp6-relay +
                  // option interface-id ifindex
                  leaf ifindex {
                    tailf:cli-no-name-on-delete;
                    type empty;
                  }


                  // service / ies * / interface * / ipv6 dhcp6-relay +
                  // option interface-id string
                  leaf string {
                    tailf:cli-no-name-on-delete;
                    tailf:cli-no-value-on-delete;
                    type string;
                  }
                }
              }

              // service / ies * / interface * / ipv6 dhcp6-relay +
              // option remote-id
              leaf remote-id {
                type empty;
              }
            }

            // service / ies * / interface * / ipv6 dhcp6-relay / source-address
            leaf source-address {
              tailf:cli-embed-no-on-delete;
              tailf:cli-case-insensitive;
              type inet:ipv6-address;
            }

            // service / ies * / interface * / ipv6 dhcp6-relay / link-address
            leaf link-address {
              tailf:cli-embed-no-on-delete;
              type inet:ipv6-address;
            }

            // service / ies * / interface * / ipv6 dhcp6-relay / server *
            list server {
              tailf:cli-embed-no-on-delete;
              tailf:cli-suppress-mode;
              max-elements 8;
              key ipv6z-address;
              leaf ipv6z-address {
                type inet:ipv6-address;
              }
            }

            // service / ies * / interface * / ipv6 dhcp6-relay / shutdown
            leaf shutdown {
              tailf:cli-boolean-no;
              default true;
              type boolean;
            }
          }

          // service / ies * / interface * / ipv6 / urpf-check /
          container urpf-check {
            tailf:cli-add-mode;

            // service / ies * / interface * / ipv6 / urpf-check /
            // ignore-default
            leaf ignore-default {
              tailf:cli-embed-no-on-delete;
              type empty;
            }

            // service / ies * / interface * / ipv6 / urpf-check / mode
            container mode {
              tailf:cli-embed-no-on-delete;
              choice choice {

                // service / ies * / interface * / ipv6 / urpf-check mode
                // strict
                leaf strict {
                  tailf:cli-no-name-on-delete;
                  type empty;
                }

                // service / ies * / interface * / ipv6 / urpf-check mode
                // loose
                leaf loose {
                  tailf:cli-no-name-on-delete;
                  type empty;
                }

                // service / ies * / interface * / ipv6 / urpf-check
                // mode strict-no-ecmp
                leaf strict-no-ecmp {
                  tailf:cli-no-name-on-delete;
                  type empty;
                }
              }
            }
          }
        }

        // service / ies * / interface * / sap *
        list sap {
          tailf:info "Provision a SAP";
          tailf:cli-embed-no-on-delete;
          max-elements 1;
          key sap-id;

          leaf sap-id {
            tailf:cli-diff-dependency "/alu:service/epipe/sap"
              + "[sap-id=current()/../sap-id]" {
              tailf:cli-trigger-on-set;
            }
            tailf:cli-diff-dependency "/alu:service/vpls/sap"
              + "[sap-id=current()/../sap-id]" {
              tailf:cli-trigger-on-set;
            }
            tailf:cli-diff-dependency "/alu:service/vprn/interface/sap"
              + "[sap-id=current()/../sap-id]" {
              tailf:cli-trigger-on-set;
            }
            tailf:cli-diff-dependency "/alu:service/ies/interface/sap"
              + "[sap-id=current()/../sap-id]" {
              tailf:cli-trigger-on-set;
            }
            tailf:info "<sap-id>;;different formats depending on port mode";
            type string;
          }

          // service / ies * / interface * / sap * / create
          leaf create {
            mandatory true;
            type empty;
            tailf:cli-hide-in-submode;
            tailf:cli-no-name-on-delete;
          }

          // service / ies * / interface * / sap * / description
          leaf description {
            tailf:info "Description for the SAP";
            tailf:cli-embed-no-on-delete;
            tailf:cli-no-value-on-delete;
            type string;
          }

          // service / ies * / interface * / sap * / egress
          container egress {
            tailf:info "Configure egress policies";
            tailf:cli-add-mode;

            // service / ies * / interface * / sap * / egress / agg-rate-limit
            container agg-rate-limit {
              tailf:info "Configure the aggregate rate limit";
              tailf:cli-embed-no-on-delete;
              tailf:cli-compact-syntax;
              tailf:cli-sequence-commands;

              leaf agg-rate {
                tailf:cli-drop-node-name;
                tailf:cli-no-value-on-delete;
                type union {
                  type uint32 {
                    range "1..40000000";
                  }
                  type enumeration {
                    enum max;
                  }
                }
              }

              leaf queue-frame-based-accounting {
                tailf:cli-no-name-on-delete;
                type empty;
              }
            }

            // service / ies * / interface * / sap * / egress / filter
            container filter {
              tailf:info "Apply egress filter";
              tailf:cli-embed-no-on-delete;

              leaf ip {
                type union {
                  type string {
                    length "1..64";
                  }
                  type uint16 {
                    range "1..65535";
                  }
                }
              }

              leaf ipv6 {
                type union {
                  type string {
                    length "1..64";
                  }
                    type uint16 {
                    range "1..65535";
                  }
                }
              }
            }

            // service / ies * / interface * / sap * / egress /
            // policer-control-policy
            leaf policer-control-policy {
              tailf:info "Specify policer control policy";
              tailf:cli-no-value-on-delete;
              tailf:non-strict-leafref {
                path "/alu:qos/policer-control-policy/name";
              }
              type string;
            }

            // service / ies * / interface * / sap * / egress /
            // qinq-mark-top-only
            leaf qinq-mark-top-only {
              tailf:info "Mark p-bits on top q-tag only";
              type empty;
            }

            // service / ies * / interface * / sap * / egress / qos
            leaf qos {
              tailf:info "Apply egress qos policy";
              tailf:cli-embed-no-on-delete;
              type uint16;
              tailf:non-strict-leafref {
                path "/alu:qos/sap-egress/policy-id";
              }
            }

            // service / ies * / interface * / sap * / egress /  queue-override
            container queue-override {
              tailf:info "Apply queue override";
              tailf:cli-add-mode;
              uses queue-override-grouping;
            }

            // service / ies * / interface * / sap * / egress / scheduler-policy
            leaf scheduler-policy {
              tailf:info "Specify a scheduler-policy";
              tailf:cli-no-value-on-delete;
              tailf:non-strict-leafref {
                path "/alu:qos/scheduler-policy/scheduler-policy-name";
              }
              type string;
            }
          }

          // service / ies * / interface * / sap * / ingress
          container ingress {
            tailf:info "Configure ingress policies";
            tailf:cli-add-mode;

            // service / ies * / interface * / sap * / ingress / qos
            leaf qos {
              tailf:cli-embed-no-on-delete;
              type uint16;
              tailf:non-strict-leafref {
                path "/alu:qos/sap-ingress/policy-id";
              }
            }

            // service / ies * / interface * / sap * / ingress / filter
            container filter {
              tailf:info "Apply ingress filter";
              tailf:cli-embed-no-on-delete;

              // service / ies * / interface * / sap * / ingress / filter ip
              leaf ip {
                type union {
                  type string {
                    length "1..64";
                  }
                  type uint16 {
                    range "1..65535";
                  }
                }
              }

              // service / ies * / interface * / sap * / ingress / filter ipv6
              leaf ipv6 {
                type union {
                  type string {
                    length "1..64";
                  }
                  type uint16 {
                    range "1..65535";
                  }
                }
              }
            }

            // service / ies * / interface * / sap * / ingress /  queue-override
            container queue-override {
              tailf:info "Apply queue override";
              tailf:cli-add-mode;
              uses queue-override-grouping;
            }
          }

          // service / ies * / interface * / sap * / anti-spoof
          leaf anti-spoof {
            tailf:info "Configures anti-spoof filtering for this SAP";
            type enumeration {
              enum "nh-mac";
            }
          }

          // service / ies * / interface * / sap * / multi-service-site
          leaf multi-service-site {
            tailf:info "Specify the multi-service-site to which this"
                      +" SAP belongs";
            tailf:cli-embed-no-on-delete;
            type leafref {
              path "/alu:service/customer/multi-service-site"
                 + "/customer-site-name";
            }
          }

          // service / ies * / interface * / sap * / sub-sla-mgmt
          container sub-sla-mgmt {
            presence present;
            tailf:cli-add-mode;

            // service / ies * / interface * / sap * / sub-sla-mgmt / +
            // def-sub-id
            leaf def-sub-id {
              type enumeration {
                enum "use-sap-id";
              }
            }

            // service / ies * / interface * / sap * / sub-sla-mgmt / +
            // def-sub-profile
            leaf def-sub-profile {
              type string;
            }

            // service / ies * / interface * / sap * / sub-sla-mgmt / +
            // single-sub-parameters
            container single-sub-parameters {
              presence present;
              tailf:cli-add-mode;

              // service / ies * / interface * / sap * / sub-sla-mgmt / +
              // single-sub-parameters / profiled-traffic-only
              leaf profiled-traffic-only {
                type empty;
              }
            }

            // service / ies * / interface * / sap * / sub-sla-mgmt / +
            // shutdown
            leaf shutdown {
              tailf:cli-boolean-no;
              default true;
              type boolean;
            }
          }

          // service / ies * / interface * / sap * / calling-station-id
          leaf calling-station-id {
            tailf:info "Configure the RADIUS calling-station-id to include"
                      +" in auth/acct requests";
            type string;
          }

          // service / ies * / interface * / sap * / shutdown
          leaf shutdown {
            tailf:info "Administratively enable/disable SAP";
             type empty;
          }
        }
        // service / ies * / interface * / tos-marking-state
        leaf tos-marking-state {
          tailf:info "Specify TOS marking state";
          tailf:cli-no-value-on-delete;
          tailf:cli-trim-default;
          type enumeration {
            enum trusted;
            enum untrusted;
          }
          default untrusted;
        }

        // service / ies * / interface * / urpf-check /
        container urpf-check {
          tailf:info "Enables/Configures unicast RPF check for an interface";
          tailf:cli-add-mode;

          // service / ies * / interface * / urpf-check / mode
          leaf mode {
            tailf:cli-no-value-on-delete;
            type enumeration {
              enum strict;
              enum loose;
              enum strict-no-ecmp;
            }
          }
        }

        // service / ies * / interface * / shutdown
        leaf shutdown {
          tailf:info "Administratively enable/disable interface";
          type empty;
        }
      }

      // service / ies * / shutdown
      leaf shutdown {
        tailf:cli-boolean-no;
        default true;
        type boolean;
      }
    }

    // service / vpls *
    list vpls {
      tailf:info "Provision a Virtual Private LAN Service";
      tailf:cli-recursive-delete;
      // Dependency between sap ids and port/lag names.
      tailf:cli-diff-dependency "/alu:port";
      tailf:cli-diff-dependency "/alu:lag";

      key service-id;
      leaf service-id {
        type vpls-id;
      }

      // service / vpls * / customer
      leaf customer {
        tailf:info "<customer-id>;;[1..2147483647]>";
        tailf:cli-hide-in-submode;
        tailf:cli-no-name-on-delete;
        tailf:cli-no-value-on-delete;
        type leafref {
          path "/alu:service/customer/customer-id";
        }
      }

      // service / vpls * / vpn
      leaf vpn {
        tailf:info "<vpn-id>;;[1..2147483647]";
        tailf:cli-hide-in-submode;
        type uint32 {
          range "1..2147483647";
        }
      }

      // service / vpls * / m-vpls
      leaf m-vpls {
        tailf:info "<m-vpls>;;keyword - creates a management VPLS";
        tailf:cli-hide-in-submode;
        type empty;
      }

      // service / vpls * / b-vpls
      choice a {
        leaf b-vpls {
          tailf:info "<b-vpls>;; keyword b-vpls - PBB backbone-vpls";
          tailf:cli-hide-in-submode;
          type empty;
        }

        // service / vpls * / i-vpls
        leaf i-vpls {
          tailf:info "<i-vpls>;; keyword i-vpls - PBB backbone-vpls";
          tailf:cli-hide-in-submode;
          type empty;
        }
      }

      // service / vpls * / description
      leaf description {
        tailf:info "Description for the service";
        tailf:cli-embed-no-on-delete;
        tailf:cli-no-value-on-delete;
        type string;
      }

      // service / vpls * / disable-learning
      leaf disable-learning {
        tailf:info "Enable/disable learning of new MAC addresses";
        tailf:cli-embed-no-on-delete;
        type empty;
      }

      // service / vpls * / disable-aging
      leaf disable-aging {
        tailf:info "Enable/disable aging of MAC addresses";
        tailf:cli-embed-no-on-delete;
        type empty;
      }

      // service / vpls * / discard-unknown
      leaf discard-unknown {
        tailf:cli-embed-no-on-delete;
        tailf:info "Enable/disable discarding of packets with "
          + "unknown destination";
        type empty;
      }

      // service / vpls * / allow-ip-int-binding
      leaf allow-ip-int-binding {
        tailf:info "Enable/disable IP int binding";
        tailf:cli-embed-no-on-delete;
        type empty;
      }

      // service / vpls * / service-name
      leaf service-name {
        tailf:info "Configure service name";
        tailf:cli-embed-no-on-delete;
        tailf:cli-no-value-on-delete;
        type string;
      }


      // service / vpls * / eth-cfm /
      container eth-cfm {
        tailf:info "Configure CFM parameters";
        tailf:cli-add-mode;
        uses eth-cfm;

        // service / vpls * / eth-cfm / tunnel-fault
        leaf tunnel-fault {
          type enumeration {
            enum accept;
            enum ignore;
          }
        }
      }

      // service / vpls * / fdb-table-high-wmark
      leaf fdb-table-high-wmark {
        tailf:info "Configure the high watermark for the FDB table";
        tailf:cli-embed-no-on-delete;
        tailf:cli-no-value-on-delete;
        type uint8 {
          range "0..100";
        }
      }

      // service / vpls * / fdb-table-low-wmark
      leaf fdb-table-low-wmark {
        tailf:info "Configure the low watermark for the FDB table";
        tailf:cli-embed-no-on-delete;
        tailf:cli-no-value-on-delete;
        type uint8 {
          range "0..100";
        }
      }

      // service / vpls * / fdb-table-size
      leaf fdb-table-size {
        tailf:info "Configure the maximum number of MAC entries in the FDB";
        tailf:cli-embed-no-on-delete;
        tailf:cli-no-value-on-delete;
        type uint32;
      }

      // service / vpls * / igmp-snooping /
      container igmp-snooping {
        tailf:info "Configure IGMP snooping parameters";
        tailf:cli-add-mode;

        // service / vpls * / igmp-snooping / query-interval
        leaf query-interval {
          tailf:info "Configure the IGMP Query Interval for v1/v2 Queriers";
          tailf:cli-embed-no-on-delete;
          tailf:cli-no-value-on-delete;
          type uint16 {
            range "0..1024";
          }
        }

        // service / vpls * / igmp-snooping / report-src-ip
        leaf report-src-ip {
          tailf:info "Configure the IP source address used in IGMP queries";
          tailf:cli-embed-no-on-delete;
          tailf:cli-no-value-on-delete;
          type inet:ipv4-address;
        }

        // service / vpls * / igmp-snooping / robust-count
        leaf robust-count {
          tailf:info "Configure the IGMP Robustness Variable for"
            + " v1/v2 Queriers";
          tailf:cli-no-value-on-delete;
          type uint32;
        }

        // service / vpls * / igmp-snooping * / shutdown
        leaf shutdown {
          tailf:info "Administratively enable or disable IGMP snooping";
          tailf:cli-boolean-no;
          default true;
          type boolean;
        }
      }

      // service / vpls * / interface
      list interface {
        tailf:info "Create/delete or configure an IP interface";
        tailf:cli-embed-no-on-delete;
        key ip-int-name;
        leaf ip-int-name {
            type string;
        }

        // service / vpls * / interface * / create
        leaf create {
          tailf:cli-hide-in-submode;
          tailf:cli-no-name-on-delete;
          mandatory true;
          type empty;
        }

        // service / vpls * / interface * / address
        container address {
          tailf:info "Assigns an IP address/IP subnet/broadcast address format"
                     + " to the interface";
          tailf:cli-embed-no-on-delete;
          tailf:cli-sequence-commands;
          tailf:cli-compact-syntax;

          choice a {
            leaf addr-and-prefix {
              tailf:cli-drop-node-name;
              tailf:cli-no-value-on-delete;
              type tailf:ipv4-address-and-prefix-length;
            }
            case addr-and-netmask {
              leaf addr {
                tailf:cli-drop-node-name;
                tailf:cli-no-value-on-delete;
                type inet:ipv4-address;
              }
              leaf mask {
                tailf:cli-drop-node-name;
                tailf:cli-no-value-on-delete;
                type inet:ipv4-address;
              }
            }
          }
        }

        // service / vpls * / interface * / arp-timeout
         leaf arp-timeout {
           tailf:info "Configures timeout for an ARP entry learned"
                       +" on the interface";
           tailf:cli-no-value-on-delete;
           type uint16;
         }

        // service / vpls * / interface * / description
         leaf description {
           tailf:info "Description for VPLS interface";
           tailf:cli-no-value-on-delete;
           type string;
         }

        // service / vpls * / interface * / mac
        leaf mac {
          tailf:info "Assign a MAC address to the interface";
          tailf:cli-no-value-on-delete;
          type ieee-mac;
        }

        // service / vpls * / interface * / static-arp
        list static-arp {
          tailf:info "Configure a static ARP entry for the interface";
          tailf:cli-suppress-mode;
          tailf:cli-sequence-commands;
          tailf:cli-embed-no-on-delete;
          key address;
          leaf address {
            type inet:ipv4-address;
          }

          leaf ieee-address {
            tailf:info "xx:xx:xx:xx:xx:xx or xx-xx-xx-xx-xx-xx";
            tailf:cli-drop-node-name;
            type ieee-mac;
          }

          leaf unnumbered {
            type empty;
          }
        }

        // service / vpls * / interface * / unnumbered
        leaf unnumbered {
          tailf:info "Configure the interface as an unnumbered interface";
          tailf:cli-no-value-on-delete;
          type union {
            type inet:ipv4-address;
            type string;
          }
        }

        // service / vpls * / interface * / shutdown
        leaf shutdown {
          tailf:info "Administratively enable/disable the interface";
          tailf:cli-boolean-no;
          default true;
          type boolean;
        }
      }

      // service / vpls * / local-age
      leaf local-age {
        tailf:info "Configure aging time for locally learned mac addresses";
        tailf:cli-embed-no-on-delete;
        tailf:cli-no-value-on-delete;
        type uint32 {
          range "60..86400";
        }
      }

      // service / vpls * / mac-move
      container mac-move {
        tailf:info "Configure Mac Move and its attributes";
        tailf:cli-embed-no-on-delete;
        tailf:cli-add-mode;

        // service / vpls * / mac-move / move-frequency
        leaf move-frequency {
          tailf:info "Configure move frequency to be used";
          tailf:cli-embed-no-on-delete;
          tailf:cli-no-value-on-delete;
          type uint8 {
            range "1..100";
          }
        }

        // service / vpls * / mac-move / retry-timeout
        leaf retry-timeout {
          tailf:info "Configure retry timeout to be used";
          tailf:cli-embed-no-on-delete;
          tailf:cli-no-value-on-delete;
          type uint8 {
            range "0..120";
          }
        }

        // service / vpls * / mac-move / shutdown
        leaf shutdown {
          tailf:info "Administratively enable/disable mac-move";
          tailf:cli-boolean-no;
          default false;
          type boolean;
        }
      }

      // service / vpls * / mfib-table-high-wmark
      leaf mfib-table-high-wmark {
        tailf:info "Configure the high watermark for the MFIB table";
        tailf:cli-embed-no-on-delete;
        tailf:cli-no-value-on-delete;
        type uint8 {
          range "1..100";
        }
      }

      // service / vpls * / mfib-table-low-wmark
      leaf mfib-table-low-wmark {
        tailf:info "Configure the low watermark for the MFIB table";
        tailf:cli-embed-no-on-delete;
        tailf:cli-no-value-on-delete;
        type uint8 {
          range "1..100";
        }
      }

      // service / vpls * / mfib-table-size
      leaf mfib-table-size {
        tailf:info "Configure the maximum number of SG entries in the MFIB";
        tailf:cli-embed-no-on-delete;
        tailf:cli-no-value-on-delete;
        type uint32;
      }

      // service / vpls * / remote-age
      leaf remote-age {
        tailf:info "Configure aging time for remotely learned mac addresses";
        tailf:cli-embed-no-on-delete;
        tailf:cli-no-value-on-delete;
        type uint32 {
          range "0..86400";
        }
      }

      // service / vpls * / send-flush-on-failure
      leaf send-flush-on-failure {
        tailf:info "Enable/disable sending MAC withdraw message"
          + " on SAP/Spoke-SDP failure";
        tailf:cli-embed-no-on-delete;
        type empty;
      }

      // service / vpls * / service-mtu
      leaf service-mtu {
        tailf:info "Configure service MTU";
        tailf:cli-embed-no-on-delete;
        tailf:cli-no-value-on-delete;
        type uint16 {
          range "0..9194";
        }
      }

      // service / vpls * / spb
      list spb {
        tailf:info "Configure Shortest Path Bridging";
        tailf:cli-embed-no-on-delete;
        key isis-instance;

        leaf isis-instance {
          tailf:info "<isis instance>;<1024..2047>";
          type uint16 {
            range "1024..2047";
          }
        }

        // service / vpls * / fid
        leaf fid {
          tailf:info "<fid>;;<1..4095>";
          tailf:cli-hide-in-submode;
          tailf:cli-no-name-on-delete;
          tailf:cli-no-value-on-delete;
          type uint16 {
            range "1..4095";
          }
        }

        // service / vpls * / spb / level *
        list level {
          tailf:info "Configure SPB level information";
          tailf:cli-embed-no-on-delete;
          key level;
          leaf level {
            type uint32;
          }

          // service / vpls * / spb / level * / bridge-priority
          leaf bridge-priority {
            tailf:info "Configure bridge priority";
            tailf:cli-no-name-on-delete;
            tailf:cli-no-value-on-delete;
            type uint8 {
              range "0..15";
            }
          }

          // service / vpls * / spb / level * / ect-algorithm
          container ect-algorithm {
            tailf:info "Configure ECT algorithm of forwarding range";

            // service / vpls * / spb / level * / ect-algorithm / fid-range
            leaf fid-range {
              tailf:info "<fid-range>;;<1..4095>-<1..4095>";
              tailf:cli-no-name-on-delete;
              tailf:cli-no-value-on-delete;
              type string;
            }

            // service / vpls * / spb / level * / ect-algorithm / path-id
            leaf path-id {
              tailf:cli-no-name-on-delete;
              tailf:cli-drop-node-name;
              type enumeration {
                enum low-path-id;
                enum high-path-id;
              }
            }
          }

          // service / vpls * / spb / level * / forwarding-tree-topology
          container forwarding-tree-topology {
            tailf:info "Configure forwarding tree topology parameters";

            // service / vpls * / spb / level * / ect-algorithm / unicast
            leaf unicast {
              tailf:cli-no-name-on-delete;
              type enumeration {
                enum spf;
                enum st;
              }
            }
          }

          // service / vpls * / spb / level * / hello-interval
          leaf hello-interval {
            tailf:cli-embed-no-on-delete;
            tailf:cli-no-value-on-delete;
            type uint16 {
              range "0..20000";
            }
          }

          // service / vpls * / spb / level * / hello-multiplier
          leaf hello-multiplier {
            tailf:cli-embed-no-on-delete;
            type uint8 {
              range "2..100";
            }
          }

          // service / vpls * / spb / level * / metric
          leaf metric {
            tailf:cli-embed-no-on-delete;
            tailf:cli-no-value-on-delete;
            type uint16;
          }
        }

        // service / vpls * / spb / lsp-pacing-interval
        leaf lsp-pacing-interval {
          tailf:cli-embed-no-on-delete;
          tailf:cli-no-value-on-delete;
          type uint32;
        }

        // service / vpls * / spb / retransmit-interval
        leaf retransmit-interval {
          tailf:cli-embed-no-on-delete;
          type uint32;
        }

        // service / vpls * / spb / shutdown
        leaf shutdown {
          tailf:info "Administratively enable or disable the operation of ISIS";
          tailf:cli-boolean-no;
          default true;
          type boolean;
        }

        // service / vpls * / spb
        leaf create {
          tailf:cli-hide-in-submode;
          tailf:cli-no-name-on-delete;
          mandatory true;
          type empty;
        }
      }

      // service / vpls * / stp
      container stp {
        tailf:cli-add-mode;

        //  service / vpls * / stp / forward-delay
        leaf forward-delay {
          tailf:info "Configure forward-delay";
          tailf:cli-embed-no-on-delete;
          tailf:cli-no-value-on-delete;
          type uint8 {
            range "4..30";
          }
        }

        //  service / vpls * / stp / hello-time
        leaf hello-time {
          tailf:info "Configure hello-time";
          tailf:cli-embed-no-on-delete;
          tailf:cli-no-value-on-delete;
          type uint8 {
            range "1..10";
          }
        }

        //  service / vpls * / stp / hold-count
        leaf hold-count {
          tailf:info "Configure BPDU txmit hold count";
          tailf:cli-embed-no-on-delete;
          tailf:cli-no-value-on-delete;
          type uint8 {
            range "1..10";
          }
        }

        //  service / vpls * / stp / max-age
        leaf max-age {
          tailf:info "Configure maximum info age for the stp";
          tailf:cli-embed-no-on-delete;
          tailf:cli-no-value-on-delete;
          type uint8 {
            range "6..40";
          }
        }

        //  service / vpls * / stp / mode
        leaf mode {
          tailf:info "Configure protocol version";
          tailf:cli-embed-no-on-delete;
          type enumeration {
            enum rstp;
            enum comp-dot1w;
            enum dot1w;
            enum mstp;
            enum pmstp;
          }
        }

        //  service / vpls * / stp / mst-instance *
        list mst-instance {
          tailf:info "Provision a Multiple Spanning Tree instance";
          tailf:cli-embed-no-on-delete;
          key mst-inst-number;
          leaf mst-inst-number {
            type uint16 {
              range "1..4094";
            }
          }

          //  service / vpls * / stp / mst-instance * / mst-priority
          leaf mst-priority {
            tailf:info "Configure the MST instance bridge priority";
            tailf:cli-embed-no-on-delete;
            tailf:cli-no-value-on-delete;
            type uint16;
          }

          //  service / vpls * / stp / mst-instance * / vlan-range
          leaf vlan-range {
            tailf:info "Configure range of VLANs managed by this MSTI";
            tailf:cli-embed-no-on-delete;
            tailf:cli-no-value-on-delete;
            type uint16 {
              range "0..4094";
            }
          }

          // service / vpls * / stp / mst-instance create
          leaf create {
            tailf:cli-hide-in-submode;
            mandatory true;
            type empty;
          }
        }

        //  service / vpls * / stp / mst-max-hops
        leaf mst-max-hops {
          tailf:info "Configure the max number of hops in a MSTP region";
          tailf:cli-embed-no-on-delete;
          tailf:cli-no-value-on-delete;
          type uint8 {
            range "1..40";
          }
        }

        //  service / vpls * / stp / mst-name
        leaf mst-name {
          tailf:info "Configure the MST region name";
          tailf:cli-embed-no-on-delete;
          tailf:cli-no-value-on-delete;
          type string {
            length "1..32";
          }
        }

        //  service / vpls * / stp / mst-revision
        leaf mst-revision {
          tailf:info "Configure MST configuration revision";
          tailf:cli-embed-no-on-delete;
          tailf:cli-no-value-on-delete;
          type uint16;
        }

        //  service / vpls * / stp / priority
        leaf priority {
          tailf:info "Configure bridge priority for the stp";
          tailf:cli-embed-no-on-delete;
          tailf:cli-no-value-on-delete;
          type uint16;
        }

        //  service / vpls * / stp / shutdown
        leaf shutdown {
          tailf:info "Enable/disable spanning tree protocol";
          tailf:cli-boolean-no;
          default true;
          type boolean;
        }
      }

      // service / vpls * / def-mesh-vc-id
      leaf def-mesh-vc-id {
        tailf:info "Configure default mesh vc-id";
        tailf:cli-no-name-on-delete;
        tailf:cli-no-value-on-delete;
        type uint32 {
          range "1..4294967295";
        }
      }

      // service / vpls * / mesh-sdp
      list mesh-sdp {
        tailf:cli-embed-no-on-delete;
        tailf:cli-key-format "$(1):$(2)";
        uses sdp-spoke-mesh-common;
        key "sdp-id vc-id";
      }

      // service / vpls * / pim-snooping
      container pim-snooping {
        tailf:cli-add-mode;

        leaf shutdown {
          tailf:cli-boolean-no;
          default true;
          type boolean;
        }
      }

      // service / vpls * / spoke-sdp *
      list spoke-sdp {
        tailf:cli-embed-no-on-delete;
        tailf:cli-key-format "$(1):$(2)";
        uses sdp-spoke-mesh-common;
        key "sdp-id vc-id";

        // service / vpls * / spoke-sdp * split-horizon-group
        leaf split-horizon-group {
          tailf:info "<group-name>";
          tailf:cli-hide-in-submode;
          tailf:cli-no-name-on-delete;
          tailf:cli-no-value-on-delete;
          type leafref {
            path "/alu:service/vpls/split-horizon-group/group-name";
          }
        }

        // service / vpls * / spoke-sdp * force-vlan-vc-forwarding
        leaf force-vlan-vc-forwarding {
          type empty;
        }

        // service / vpls * / spoke-sdp * / bpdu-translation
        leaf bpdu-translation {
          tailf:cli-embed-no-on-delete;
          type enumeration {
            enum auto;
            enum pvst;
            enum stp;
          }
        }

        // service / vpls * / spoke-sdp * / disable-aging
        leaf diable-aging {
          tailf:cli-embed-no-on-delete;
          type empty;
        }

        // service / vpls * / spoke-sdp * / disable-learning
        leaf disable-learning {
          tailf:cli-embed-no-on-delete;
          type empty;
        }

        // service / vpls * / spoke-sdp * / discard-unkown-source
        leaf discard-unknown-source {
          tailf:cli-embed-no-on-delete;
          type empty;
        }

        // service / vpls * / spoke-sdp * / l2pt-termination
        leaf l2pt-termination {
          tailf:cli-embed-no-on-delete;
          type empty;
        }

        // service / vpls * / spoke-sdp * / limit-mac-move
        leaf limit-mac-move {
          tailf:cli-embed-no-on-delete;
          tailf:cli-no-value-on-delete;
          type limit-mac-move;
        }

        // service / vpls * / spoke-sdp * / max-nbr-mac-addr
        leaf max-nbr-mac-addr {
          tailf:cli-embed-no-on-delete;
          tailf:cli-no-value-on-delete;
          type uint32;
        }

        // service / vpls * / spoke-sdp * / stp /
        container stp {
          tailf:cli-add-mode;
          uses stp-common;
        }

        // service / vpls * / spoke-sdp * / transit-policy
        container transit-policy {
          tailf:cli-embed-no-on-delete;

          // service / vpls * / spoke-sdp * / transit-policy prefix
          leaf prefix {
            tailf:cli-no-value-on-delete;
            type uint16 {
              range "1..65535";
            }
          }
        }
      }

      // service / vpls * / sap *
      list sap {
        tailf:info "Provision a SAP";
        tailf:cli-embed-no-on-delete;
        key sap-id;

        leaf sap-id {
          tailf:info "<sap-id>;;different formats depending on port mode";
          tailf:cli-diff-dependency "/alu:service/ies/interface/sap"
            + "[sap-id=current()/../sap-id]" {
            tailf:cli-trigger-on-set;
          }
          tailf:cli-diff-dependency "/alu:service/epipe/sap"
            + "[sap-id=current()/../sap-id]" {
            tailf:cli-trigger-on-set;
          }
          tailf:cli-diff-dependency "/alu:service/vprn/interface/sap"
              + "[sap-id=current()/../sap-id]" {
              tailf:cli-trigger-on-set;
          }
          tailf:cli-diff-dependency "/alu:service/vpls/sap"
            + "[sap-id=current()/../sap-id]" {
            tailf:cli-trigger-on-set;
          }
          type string;
        }

        // service / vpls * / sap * / split-horizon-group
        leaf split-horizon-group {
          tailf:info "<group-name>";
          tailf:cli-hide-in-submode;
          tailf:cli-no-name-on-delete;
          tailf:cli-no-value-on-delete;
          type leafref {
            path "/alu:service/vpls/split-horizon-group/group-name";
          }
        }

        // service / vpls * / sap * / accounting-policy
        leaf accounting-policy {
          tailf:cli-embed-no-on-delete;
          tailf:cli-no-value-on-delete;
          type uint8 {
            range "1..99";
          }
        }

        // service / vpls * / sap * / anti-spoof
        leaf anti-spoof {
          tailf:info "Configures anti-spoof filtering for this SAP";
          tailf:cli-embed-no-on-delete;
          tailf:cli-no-value-on-delete;
          type enumeration {
            enum ip;
            enum ip-mac;
            enum mac;
          }
        }

        // service / vpls * / sap * / app-profile
        leaf app-profile {
          tailf:info "Configure the application profile name";
          tailf:cli-embed-no-on-delete;
          tailf:cli-no-value-on-delete;
          type string {
            length "1..32";
          }
        }

        // service / vpls * / sap * / auto-learn-mac-protect
        leaf auto-learn-mac-protect {
          tailf:info "Enable/disable automatic update of MAC protect list";
          tailf:cli-embed-no-on-delete;
          type empty;
        }

        // service / vpls * / sap * / bpdu-translation
        leaf  bpdu-translation {
          tailf:cli-embed-no-on-delete;
          type enumeration {
            enum auto;
            enum pvst;
            enum stp;
          }
        }

        // service / vpls * / sap * / collect-stats
        leaf collect-stats {
          tailf:info "Enable/disable statistics collection";
          tailf:cli-embed-no-on-delete;
          type empty;
        }

        // service / vpls * / sap * / description
        leaf description {
          tailf:cli-embed-no-on-delete;
          tailf:cli-no-value-on-delete;
          type string;
        }

        // service / vpls * / sap * / disable-aging
        leaf disable-aging {
          tailf:cli-embed-no-on-delete;
          type empty;
        }

        // service / vpls * / sap * / disable-learning
        leaf disable-learning {
          tailf:cli-embed-no-on-delete;
          type empty;
        }

        // service / vpls * / sap * / discard-unknown-source
        leaf discard-unknown-source {
          tailf:cli-embed-no-on-delete;
          type empty;
        }

        // service / vpls * / sap * / eth-cfm
        container eth-cfm {
          tailf:cli-add-mode;
          uses eth-cfm;

          leaf mip {
            type empty;
          }
        }

        // service / vpls * / sap * / igmp-snooping
        container igmp-snooping {
          uses igmp-snooping;
        }

        // service / vpls * / sap * / ingress
        container ingress {
          tailf:cli-add-mode;
          uses sap-ingress-grouping;
        }

        // service / vpls * / sap * / lag-link-map-profile
        leaf lag-link-map-profile {
          tailf:cli-embed-no-on-delete;
          tailf:cli-no-value-on-delete;
          type uint8 {
            range "1..32";
          }
        }

        // service / vpls * / sap * / l2pt-termination
        leaf l2pt-termination {
          tailf:cli-embed-no-on-delete;
          type empty;
        }

        // service / vpls * / sap * / limit-mac-move
        leaf limit-mac-move {
          tailf:cli-embed-no-on-delete;
          type limit-mac-move;
        }

        // service / vpls * / sap * / mac-pinning
        leaf mac-pinning {
          tailf:cli-embed-no-on-delete;
          type empty;
        }

        // service / vpls * / sap * / managed-vlan-list
        container managed-vlan-list {
          tailf:cli-add-mode;

          // service / vpls * / sap * / managaged-vlan-list / default-sap
          leaf default-sap {
            tailf:cli-embed-no-on-delete;
            type empty;
          }

          // service / vpls * / sap * / managaged-vlan-list / range
          leaf range {
            tailf:cli-embed-no-on-delete;
            tailf:cli-no-value-on-delete;
            tailf:info "<vlan range>;;<0-4094>-<0-4094>";
            type string;
          }
        }

        // service / vpls * / sap * / max-nbr-mac-addr
        leaf  max-nbr-mac-addr {
          tailf:cli-embed-no-on-delete;
          tailf:cli-no-value-on-delete;
          type uint32 {
            range "1..4294967295";
          }
        }

        // service / vpls * / sap * / monitor-oper-group
        leaf monitor-oper-group {
          tailf:cli-embed-no-on-delete;
          tailf:cli-no-value-on-delete;
          tailf:non-strict-leafref {
            path "/alu:service/oper-group/group-name";
          }
          type string;
        }

        // service vpls * / sap * / multi-service-site
        leaf multi-service-site {
          tailf:cli-no-value-on-delete;
          type leafref {
            path "/alu:service/customer/multi-service-site/customer-site-name";
          }
          tailf:cli-diff-dependency "../egress/scheduler-policy" {
            tailf:cli-trigger-on-set;
          }
        }

        // service / vpls * / sap * / restrict-protected-src
        container restrict-protected-src {
          tailf:info "Enable/disable protected src MAC restriction";
          tailf:cli-compact-syntax;
          tailf:cli-embed-no-on-delete;
          presence present;
          leaf restrict-protected-src-value {
            tailf:cli-no-value-on-delete;
            tailf:cli-drop-node-name;
            type enumeration {
              enum alarm-only;
              enum discard-frame;
            }
          }
        }

        // service / vpls * / sap * / restrict-unprotected-dst
        leaf restrict-unprotected-dst {
          tailf:info "Enable/disable unprotected dest MAC restriction";
          tailf:cli-embed-no-on-delete;
          type empty;
        }

        // service / vpls * / sap * / ring-node
        leaf ring-node {
          tailf:info "Configure a multi-chassis ring-node for this SAP";
          tailf:cli-embed-no-on-delete;
          type empty;
        }

        // service / vpls * / sap * / static-mac
        leaf static-mac {
          tailf:info "Configure a static mac entry";
          tailf:cli-embed-no-on-delete;
          tailf:cli-no-value-on-delete;
          type ieee-mac;
        }

        // service / vpls * / sap * / egress /
        container egress {
          tailf:cli-add-mode;
          uses sap-egress-grouping;
        }

        // service / vpls * / sap * / stp
        container stp {
          tailf:info "Configure STP parameters";
          tailf:cli-add-mode;
          uses stp-common;

          // service / vpls * / sap * / stp / mst-instance *
          list mst-instance {
            tailf:info "Provision a Multiple Spanning Tree instance";
            max-elements 1;
            key mst-inst-number;

            leaf mst-inst-number {
              tailf:info "<1..4094>";
              type uint16 {
                range "1..4094";
              }
            }

            // service / vpls * / sap * / stp / mst-instance * / mst-path-cost
            leaf mst-path-cost {
              tailf:info "Configure path-cost";
              tailf:cli-no-name-on-delete;
              tailf:cli-no-value-on-delete;
              type uint32 {
                range "1..200000000";
              }
            }

            // service / vpls * / sap * / stp / mst-instance * / mst-priority
            leaf mst-priority {
              tailf:info "Configure MSTI port priority";
              tailf:cli-no-name-on-delete;
              tailf:cli-no-value-on-delete;
              type uint32;
            }
          }
        }

        // service / vpls * / sap * / tod-suite
        leaf tod-suite {
          tailf:cli-no-name-on-delete;
          tailf:cli-no-value-on-delete;
          type string;
        }

        // service / vpls * / sap * / shutdown
        leaf shutdown {
          type empty;
        }

        // service / vpls * / sap * / create
        leaf create {
          tailf:cli-hide-in-submode;
          tailf:cli-no-name-on-delete;
          mandatory true;
          type empty;
        }
      }

      // service / vpls * / split-horizon-group *
      list split-horizon-group {
        tailf:cli-embed-no-on-delete;
        tailf:info "Configure a split horizon group";
        key group-name;

        leaf group-name {
          tailf:info "<group-name>;;<32 chars max>";
          type string {
            length "1..32";
          }
        }

        // service / vpls * / split-horizon-group * residential-group
        leaf residential-group {
          tailf:cli-hide-in-submode;
          tailf:cli-no-name-on-delete;
          type empty;
        }

        // service / vpls * / split-horizon-group * create
        leaf create {
          tailf:cli-hide-in-submode;
          tailf:cli-no-name-on-delete;
          mandatory true;
          type empty;
        }

        // service / vpls * / split-horizon-group * / auto-learn-mac-protect
        leaf auto-learn-mac-protect {
          tailf:info "Enable/disable automatic update of MAC protect list";
          tailf:cli-embed-no-on-delete;
          type empty;
        }

        // service / vpls * / split-horizon-group * / description
        leaf description {
          tailf:info "Description for this group";
          tailf:cli-embed-no-on-delete;
          tailf:cli-no-value-on-delete;
          type string;
        }

        // service / vpls * / split-horizon-group * / restrict-protected-src
        leaf restrict-protected-src {
          tailf:info "Enable/disable protected src MAC restriction";
          tailf:cli-embed-no-on-delete;
          type empty;
        }

        // service / vpls * / split-horizon-group * / restrict-unprotected-src
        leaf restrict-unprotected-src {
          tailf:info "Enable/disable unprotected src MAC restriction";
          tailf:cli-embed-no-on-delete;
          type empty;
        }
      }

      // service / vpls * / create
      leaf create {
        tailf:cli-hide-in-submode;
        tailf:cli-no-name-on-delete;
        mandatory true;
        type empty;
      }

      // service / vpls * / bgp
      container bgp {
        tailf:info "Configure BGP";
        tailf:cli-recursive-delete;
        tailf:cli-add-mode;

        // service / vpls * / bgp / pw-template-binding *
        list pw-template-binding {
          tailf:info "Configure pw-template bind policy";
          key policy-id;
          leaf policy-id {
            tailf:non-strict-leafref {
              path "/alu:service/pw-template/policy-id";
            }
            type uint16;
          }
        }
      }
      // service / vpls * / bgp-ad
      container bgp-ad {
        tailf:info "Configure BGP auto-discovery";
        tailf:cli-embed-no-on-delete;
        tailf:cli-add-mode;
        presence true;

        // service / vpls * / bgp-ad / vpls-id
        leaf vpls-id {
          tailf:info "Configure VPLS-ID";
          type vpls-id;
        }

        // service / vpls * / bgp-ad / shutdown
        leaf shutdown {
          tailf:info "Administratively enable/disable BGP auto-discovery";
          tailf:cli-boolean-no;
          default true;
          type boolean;
        }
      }

      // service / vpls * / bgp-vpls
      container bgp-vpls {
        tailf:cli-add-mode;
        tailf:cli-recursive-delete;
        leaf max-ve-id {
          tailf:cli-no-name-on-delete;
          tailf:cli-no-value-on-delete;
          tailf:info "Configure maximum vpls-edge id for BGP-VPLS";
          type uint16 {
            range "1..65535";
          }
        }
        // service / vpls * / bgp-vpls / ve-name
        container ve-name {
          tailf:info "Configure vpls-edge name for BGP-VPLS";
          tailf:cli-add-mode;
          tailf:cli-compact-syntax;
          leaf ve-name-value{
            tailf:cli-hide-in-submode;
            tailf:cli-drop-node-name;
            type string;
          }
          // service / vpls * / bgp-vpls / ve-name / ve-id
          leaf ve-id {
            tailf:info "Configure vpls-edge identifier";
            tailf:cli-no-value-on-delete;
            type uint16 {
              range "1..65535";
            }
          }
        }
        // service / vpls * / bgp-vpls / shutdown
        leaf shutdown {
          tailf:info "Administratively Enable/Disable BGP-VPLS";
          type empty;
        }
      }

      // service / vpls * / shutdown
      leaf shutdown {
        tailf:info "Administratively enable/disable the service";
        tailf:cli-boolean-no;
        default true;
        type boolean;
      }
    }


    // service / vprn *
    list vprn {
      tailf:info "Provision a VPRN Service";
      tailf:cli-recursive-delete;
      // Dependency between sap ids and port/lag names.
      tailf:cli-diff-dependency "/alu:port";
      tailf:cli-diff-dependency "/alu:lag";

      key service-id;
      leaf service-id {
        type vpls-id;
      }

      // service / vprn * / customer
      leaf customer {
        tailf:info "<customer-id>;;[1..2147483647]>";
        tailf:cli-hide-in-submode;
        tailf:cli-no-name-on-delete;
        tailf:cli-no-value-on-delete;
        type leafref {
          path "/alu:service/customer/customer-id";
        }
      }

      // service / vprn * / auto-bind
      leaf auto-bind {
        tailf:cli-no-value-on-delete;
        type enumeration {
          enum ldp;
          enum gre;
          enum rsvp-te;
          enum mpls;
        }
      }

      // service / vprn * / bgp
      container bgp {
        tailf:info "Create/Configure or delete BGP instance";
        tailf:cli-embed-no-on-delete;
        tailf:cli-recursive-delete;
        tailf:cli-add-mode;

        // service / vrpn * / bgp / damping
        leaf damping         {
          tailf:info "Enable/disable BGP route damping for learned routes as"+
            "defined within the route policy";
          type empty;
        }

        // service / vprn * / bgp / router-id
        leaf router-id {
          tailf:cli-no-value-on-delete;
          type inet:ipv4-address;
        }

        // service / vprn * / bgp / group *
        list group {
          tailf:info "Configure a BGP group";
          tailf:cli-embed-no-on-delete;
          key name;
          leaf name {
            type string;
          }

          // service / vprn * / bgp / group * / as-override
          leaf as-override {
            tailf:info "Enable/disable (group level) AS override";
            type empty;
          }

          // service / vprn * / bgp / authentication-key
          container authentication-key {
            tailf:info "Configure the BGP authentication key for all peers";
            tailf:cli-embed-no-on-delete;
            tailf:cli-compact-syntax;
            tailf:cli-sequence-commands;

            leaf key {
              tailf:cli-drop-node-name;
              tailf:cli-no-value-on-delete;
              type string;
            }

            leaf type {
              tailf:cli-drop-node-name;
              tailf:cli-no-value-on-delete;
              type enumeration {
                enum hash;
                enum hash2;
              }
            }
          }

          // service / vprn * / bgp / group * / bfd-enable
          leaf bfd-enable {
            tailf:info "enables BFD sessions on this group";
            type empty;
          }

          // service / vprn * / bgp / group * / description
          leaf description {
            tailf:info "Create a textual description for the group";
            tailf:cli-no-value-on-delete;
            type string;
          }

          // service / vprn * / bgp / group * / export
          leaf-list export {
            tailf:info "Export route policies used to determine which routes"
                      +" are advertised to peers for the group";
            tailf:cli-flat-list-syntax;
            tailf:cli-no-value-on-delete;
            tailf:non-strict-leafref {
              path "/alu:router/policy-options/begin/policy-statement/name";
            }
            max-elements 5;
            type string;
          }

          // service / vprn * / bgp / group * / import
          leaf-list import {
            tailf:info "Import route policies used to determine which routes"
                      +" are accepted from peers for this group";
            tailf:cli-flat-list-syntax;
            tailf:cli-no-value-on-delete;
            max-elements 5;
            type string;
          }

          // service / vprn * / bgp / group * / local-address
          leaf local-address {
            tailf:info "Local IP address used by the group when communicating"
                      +" with BGP peers";
            tailf:cli-no-value-on-delete;
            type inet:ipv4-address;
          }

          // service / vprn * / bgp / group * / neighbor *
          list neighbor {
            tailf:info "Configure a neighbor for this group";
            tailf:cli-embed-no-on-delete;
            key address;
            leaf address {
              type union {
                type inet:ipv4-address;
                type inet:ipv6-address;
              }
            }

            // service / vprn * / bgp / group * / neighbor * /
            // advertise-inactive
            leaf advertise-inactive {
              tailf:info "Enable/disable advertising of inactive BGP routes"
                        +" to other BGP peers";
              type empty;
            }

            // service / vprn * / bgp / group * / neighbor * / description
            leaf description {
              tailf:info "Create a textual description for the neighbor";
              tailf:cli-no-value-on-delete;
              type string;
            }

            // service / vprn * / bgp / group * / neighbor * / family
            leaf-list family {
              tailf:info "Configure the IP family capability";
              tailf:cli-no-value-on-delete;
              tailf:cli-flat-list-syntax;
              type enumeration {
                enum ipv4;
                enum ipv6;
              }
            }

           // service / vprn * / bgp / group * / neighbor * / local-address
            leaf local-address {
              tailf:info "Local IP address used by the neighbor when "+
                "communicating with BGP peers";
              tailf:cli-no-value-on-delete;
              type union {
                type inet:ipv4-address;
                type inet:ipv6-address;
              }
            }

            // service / vprn * / bgp / group * / neighbor * / med-out
            leaf med-out {
              tailf:info "Enable/disable advertising the Multi-Exit "+
                "Discriminator (MED)";
              tailf:cli-no-value-on-delete;
              type union {
                type uint32;
                type enumeration {
                  enum igp-cost;
                }
              }
            }

            // service / vprn * / bgp / group * / neighbor * / multihop
            leaf multihop {
              tailf:cli-no-value-on-delete;
              type uint8 {
                range "1..255";
              }
            }

            // service / vprn * / bgp / group * / neighbor * / peer-as
            leaf peer-as {
              tailf:info "Configure (neighbor level) the AS number for"
                +" the remote peer";
              tailf:cli-no-value-on-delete;
              type uint32;
            }
            // service / vprn * / bgp / group * / neighbor * / remove-private
            container remove-private  {
              tailf:info "Remove private AS numbers from the AS Path before"
                       + " advertising to the peers for this group";
              presence true;
              leaf-list options {
                tailf:cli-drop-node-name;
                tailf:cli-flat-list-syntax;
                tailf:cli-no-value-on-delete;
                type enumeration {
                   enum limited;
                   enum skip-peer-as;
                }
              }
            }

            // service / vprn * / bgp / group * / neighbor * / split-horizon
            leaf split-horizon {
              tailf:info "Configure split horizon for the peer";
              type empty;
            }

            // service / vprn * / bgp / group * / neighbor * / type
            leaf type {
              tailf:info "Configure the peers for this group as type"
                      +" internal or external";
              tailf:cli-no-value-on-delete;
              type enumeration {
                enum internal;
                enum external;
              }
            }
          }

          // service / vprn * / bgp / group / prefix-limit
          container prefix-limit {
            tailf:info "Maximum number of routes BGP can learn";
            tailf:cli-embed-no-on-delete;
            tailf:cli-compact-syntax;
            tailf:cli-sequence-commands;

            leaf limit {
              tailf:cli-drop-node-name;
              tailf:cli-no-value-on-delete;
              type uint32;
            }

            leaf log-only {
              tailf:cli-no-name-on-delete;
              type empty;
            }

            leaf treshold {
              tailf:cli-no-name-on-delete;
              tailf:cli-no-value-on-delete;
              type uint8 {
                range "1..100";
              }
            }

            leaf idle-timeout {
              tailf:cli-no-name-on-delete;
              tailf:cli-no-value-on-delete;
              type union {
                type uint16 {
                  range "0..1024";
                }
                type enumeration {
                  enum forever;
                }
              }
            }
          }

          // service / vprn * / bgp / group * / peer-as
          leaf peer-as {
            tailf:info "Configure (group level) the AS number for"
                      +" the remote peer";
            tailf:cli-no-value-on-delete;
            type uint32;
          }

          // service / vprn * / bgp / group * / remove-private
          container remove-private  {
            tailf:info "Remove private AS numbers from the AS Path before"
                     + " advertising to the peers for this group";
            presence true;
            leaf-list options {
              tailf:cli-drop-node-name;
              tailf:cli-flat-list-syntax;
              tailf:cli-no-value-on-delete;
              type enumeration {
                 enum limited;
                 enum skip-peer-as;
              }
            }
          }

          // service / vprn * / bgp / group * / type
          leaf type {
            tailf:info "Configure the peers for this group as type"
                      +" internal or external";
            tailf:cli-no-value-on-delete;
            type enumeration {
              enum internal;
              enum external;
            }
          }

          // service / vprn * / bgp / group * / shutdown
          leaf shutdown {
            tailf:info "Administratively enable/disable the vprn bgp group";
            tailf:cli-boolean-no;
            default true;
            type boolean;
          }
        }

        // service / vprn * / bgp / med-out
        leaf med-out {
          tailf:info "Enable/disable advertising the Multi-Exit "+
            "Discriminator (MED)";
          tailf:cli-no-value-on-delete;
          type union {
            type uint32;
            type enumeration {
              enum igp-cost;
            }
          }
        }

        // service / vprn * / bgp / min-route-advertisement
        leaf min-route-advertisement {
          tailf:info "Minimum interval at which a given prefix is advertised"+
            "to a peer";
          tailf:cli-no-value-on-delete;
          type uint8 {
            range "1..255";
          }
        }

        // service / vprn * / bgp / shutdown
        leaf shutdown {
          tailf:info "Administratively enable/disable the vprn bgp";
          tailf:cli-boolean-no;
          default false;
          type boolean;
        }
      }

      // service / vprn * / description
      leaf description {
        tailf:cli-no-value-on-delete;
        type string;
      }

      // service / vprn * / dhcp
      container dhcp {
        tailf:info "Configure local DHCP servers for VPRN services";
        tailf:cli-add-mode;
        tailf:cli-recursive-delete;
        // service / vprn * / dhcp / local-dhcp-server *
        list local-dhcp-server {
          tailf:info "Configure the local DHCP server";
          tailf:cli-embed-no-on-delete;
          key server-name;
          leaf server-name {
            type string;
          }

          // service / vprn * / dhcp / local-dhcp-server * / description
          leaf description {
            tailf:info "Description for this local DHCP server";
            tailf:cli-no-value-on-delete;
            type string;
          }

          // service / vprn * / dhcp / local-dhcp-server * / force-renews
          leaf force-renews {
            tailf:info "Enable/disable sending FORCERENEW messages";
            type empty;
          }
          // service / vprn * / dhcp / local-dhcp-server * / pool
          list pool{
            tailf:info "Configure an IP address pool";
            key "pool-id";
            leaf pool-id{
              type string{
                length "1..32";
              }
            }
            // service / vprn * / dhcp / local-dhcp-server * / pool * / create
            leaf create {
              tailf:cli-hide-in-submode;
              tailf:cli-no-name-on-delete;
              mandatory true;
              type empty;
            }


            // service / vprn * / dhcp / local-dhcp-server * / pool /
            // description
            leaf description {
              type string{
                length "1..80";
              }
            }
            // service / vprn * / dhcp / local-dhcp-server * / pool /
            // failover
            // Not implemented

            // service / vprn * / dhcp / local-dhcp-server * / pool /
            // max-lease-time
            container max-lease-time {
              tailf:info "Configure the maximum lease time";
              tailf:cli-compact-syntax;
              uses dhcp-lease-time;
            }
            // service / vprn * / dhcp / local-dhcp-server * / pool /
            // min-lease-time
            container min-lease-time {
              tailf:info "Configure the minimum lease time";
              tailf:cli-compact-syntax;
              uses dhcp-lease-time;
            }
            // service / vprn * / dhcp / local-dhcp-server * / pool /
            // minimum-free
            container minimum-free {
              tailf:info "Configure the minimum number of free addresses";
              tailf:cli-compact-syntax;
              leaf minimum-free-value{
                tailf:cli-drop-node-name;
                type uint16{
                  range "0..255";
                }
              }
              // service / vprn * / dhcp / local-dhcp-server * / pool /
              // minimum-free percent
              leaf percent {
                tailf:info "Indicates the value indicates a percentage";
                type empty;
              }
              // service / vprn * / dhcp / local-dhcp-server * / pool /
              // minimum-free event-when-depleted
              leaf event-when-depleted {
                type empty;
              }
            }
            // service / vprn * / dhcp / local-dhcp-server * / pool /
            // nak-non-matching-subnet
            leaf nak-non-matching-subnet {
              tailf:info "Configure this server to reply with DHCPNAK to "+
                "DHCPREQUEST for a subnet that does not match any range "+
                "in this pool (rather than silently drop the request)";
              type empty;
            }
            container offer-time {
              // service / vprn * / dhcp / local-dhcp-server * / pool /
              // offer-time min
              leaf min {
                type uint16 {
                  range "0..59";
                }
              }
              // service / vprn * / dhcp / local-dhcp-server * / pool /
              // offer-time sec
              leaf sec {
                type uint16 {
                  range "0..59";
                }
              }
            }
            // service / vprn * / dhcp / local-dhcp-server * / pool /
            // options
            container options {
              tailf:cli-add-mode;
              // service / vprn * / dhcp / local-dhcp-server * / pool /
              // options / dns-server
              leaf-list dns-server {
                tailf:info "Configure the DNS server";
                tailf:cli-flat-list-syntax;
                tailf:cli-no-value-on-delete;
                type inet:ipv4-address;
              }
              // service / vprn * / dhcp / local-dhcp-server * / pool /
              // options / domain-name
              leaf domain-name {
                tailf:info "Configure the domain name";
                type string {
                  length "1..127";
                }
              }
              // service / vprn * / dhcp / local-dhcp-server * / pool /
              // options / lease-renew-time
              container lease-rebind-time {
                tailf:info "Configure the lease rebind time";
                tailf:cli-compact-syntax;
                uses dhcp-lease-time;
              }
              // service / vprn * / dhcp / local-dhcp-server * / pool /
              // options / lease-renew-time
              container lease-renew-time {
                tailf:info "Configure the lease renew time";
                tailf:cli-compact-syntax;
                uses dhcp-lease-time;
              }
              // service / vprn * / dhcp / local-dhcp-server * / pool /
              // options / lease-time
              container lease-time {
                tailf:info "Configure the lease time";
                tailf:cli-compact-syntax;
                uses dhcp-lease-time;
              }
              // service / vprn * / dhcp / local-dhcp-server * / pool /
              // options / netbios-name-server
              leaf-list netbios-name-server {
                tailf:info "Configure the netbios name server";
                tailf:cli-flat-list-syntax;
                tailf:cli-no-value-on-delete;
                type inet:ipv4-address;
              }
              // service / vprn * / dhcp / local-dhcp-server * / pool /
              // options / netbios-node-type
              leaf netbios-node-type {
                tailf:info "Configure the netbios node type";
                type enumeration {
                  enum "B";
                  enum "P";
                  enum "M";
                  enum "H";
                }
              }
            }
            // service / vprn * / dhcp / local-dhcp-server * / pool * /
            // subnet
            list subnet {
              tailf:info "Configure a subnet";
              key subnet-id;
              leaf subnet-id{
                type tailf:ipv4-address-and-prefix-length;
              }
            // service / vprn * / dhcp / local-dhcp-server * / pool * /
            // subnet * / create
              leaf create {
                tailf:cli-hide-in-submode;
                tailf:cli-no-name-on-delete;
                mandatory true;
                type empty;
              }
              // service / vprn * / dhcp / local-dhcp-server * / pool */
              // subnet * / address-range
              container address-range {
                tailf:info "Include range of IP addresses";
                uses ip-address-range;
              }
              // service / vprn * / dhcp / local-dhcp-server * / pool */
              // subnet * / drain
              leaf drain {
                tailf:info "Configure the subnet draining";
                type empty;
              }
              // service / vprn * / dhcp / local-dhcp-server * / pool */
              // subnet * / exclude-addresses
              container exclude-addresses {
                tailf:info "Exclude range of IP addresses";
                uses ip-address-range;
              }
              // service / vprn * / dhcp / local-dhcp-server * / pool */
              // subnet * / maximum-declined
              leaf maximum-declined  {
                tailf:info "Configure the maximum number of "+
                  "declined addresses";
                type uint32 {
                  range "0..4294967295";
                }
              }
              // service / vprn * / dhcp / local-dhcp-server * / pool */
              // subnet * / minimum-free
              container minimum-free {
                tailf:info "Configure the minimum number of free addresses";
                leaf minimum-free-value{
                  tailf:cli-drop-node-name;
                  type uint16{
                    range "0..255";
                  }
                }
                // service / vprn * / dhcp / local-dhcp-server * / pool */
                // subnet * / minimum-free percent
                leaf percent {
                  tailf:info "Indicates the value indicates a percentage";
                  type empty;
                }
                // service / vprn * / dhcp / local-dhcp-server * / pool */
                // subnet * / minimum-free event-when-deplated
                leaf event-when-depleted {
                  type empty;
                }
              }
              container options {
                tailf:cli-add-mode;
                // service / vprn * / dhcp / local-dhcp-server * / pool */
                // subnet * / options / custom-options
                //leaf custom-option{
                //  tailf:info "Configure a DHCP option";
                //}
                // service / vprn * / dhcp / local-dhcp-server * / pool */
                // subnet * / options / default-router
                leaf-list default-router {
                  tailf:info "Configure the default router";
                  tailf:cli-flat-list-syntax;
                  tailf:cli-no-value-on-delete;
                  type inet:ipv4-address;
                }
                // service / vprn * / dhcp / local-dhcp-server * / pool */
                // subnet * / options / subnet-mask
                leaf subnet-mask {
                  tailf:info "Configure the subnet mask";
                  type inet:ipv4-address;
                }
              }
            }
          }

          // service / vprn * / dhcp / local-dhcp-server * / create
          leaf create {
            tailf:cli-hide-in-submode;
            tailf:cli-no-name-on-delete;
            mandatory true;
            type empty;
          }

          // service / vprn * / dhcp / local-dhcp-server * / shutdown
          leaf shutdown {
            tailf:info "Administratively enable/disable the local DHCP server";
            tailf:cli-boolean-no;
            type boolean;
          }
        }
      }

      // service / vprn * / interface *
      list interface {
        tailf:info "Create/delete or configure an IP interface";
        tailf:cli-recursive-delete;
        tailf:cli-embed-no-on-delete;
        key ip-int-name;
        leaf ip-int-name {
          type string {
            length "1..32";
          }
        }

        // service / vprn * / interface * create
        leaf create {
          tailf:cli-hide-in-submode;
          tailf:cli-no-name-on-delete;
          mandatory true;
          type empty;
        }

        // service / vprn * / interface * tunnel
        leaf tunnel {
          tailf:cli-hide-in-submode;
          tailf:cli-no-name-on-delete;
          type empty;
        }

        // service / vprn * / interface * / address
        leaf address {
          tailf:info "Assigns an IP address format to the interface";
          type tailf:ipv4-address-and-prefix-length;
        }

        // service / vprn * / interface * / bfd
        container bfd {
          tailf:info "Configure BFD parameters";
          tailf:cli-embed-no-on-delete;
          tailf:cli-compact-syntax;
          tailf:cli-sequence-commands;

          leaf id {
            tailf:cli-drop-node-name;
            tailf:cli-no-value-on-delete;
            type uint32;
          }

          leaf receive {
            tailf:cli-no-name-on-delete;
            tailf:cli-no-value-on-delete;
            type uint32;
          }

          leaf multiplier {
            tailf:cli-no-name-on-delete;
            tailf:cli-no-value-on-delete;
            type uint32;
          }

          leaf type {
            tailf:cli-no-name-on-delete;
            tailf:cli-no-value-on-delete;
            type enumeration {
              enum cpm-np;
            }
          }
        }

        // service / vprn * / interface * / dhcp
        container dhcp{
          tailf:cli-add-mode;
          leaf description {
            tailf:info "Add/remove a text description for DHCP";
            tailf:cli-no-value-on-delete;
            type string;
          }
          // service / vprn * / interface * / dhcp / gi-address
          container gi-address {
            tailf:info "Configure the gateway interface address for the "+
              "DHCP relay";
            tailf:cli-compact-syntax;
            leaf gi-address-value{
              tailf:cli-drop-node-name;
              tailf:cli-no-value-on-delete;
              type inet:ipv4-address;
            }
            // service / vprn * / interface * / dhcp / gi-address src-ip-address
            leaf src-ip-addr {
              tailf:cli-no-value-on-delete;
              tailf:info "Use the gi-address as src-ip";
              type empty;
            }
          }
          // service / vprn * / interface * / dhcp / lease-populate
          leaf lease-populate {
            tailf:info "Configure the maximum number of DHCPv4 leases";
            tailf:cli-no-value-on-delete;
            type uint16{
              range "1..32767";
            }
          }
          // service / vprn * / interface * / dhcp / server
          leaf-list server {
            tailf:info "Configure the DHCP server IP address";
            tailf:cli-flat-list-syntax;
            tailf:cli-no-value-on-delete;
            type inet:ipv4-address;
          }
          // service / vprn * / interface * / dhcp / trusted
          leaf trusted {
            tailf:info "Enable/disable relaying of untrusted packets";
            type empty;
          }
          // service / vprn * / interface * / dhcp / use-arp
          leaf use-arp {
            tailf:info "enable/disable the use of ARP to determine the "+
              "destination Hw address";
            type empty;
          }
          // service / vprn * / interface * / dhcp / shutdown
          leaf shutdown {
            tailf:info "Administratively enable/disable DHCP on this interface";
            tailf:cli-boolean-no;
            default true;
            type boolean;
          }
        }

        // service / vprn * / interface * / secondary
        leaf secondary {
          tailf:info "Assigns a secondary IP address format to the interface";
          type tailf:ipv4-address-and-prefix-length;
        }

        // service / vprn * / interface / description
        leaf description {
          tailf:cli-no-value-on-delete;
          type string;
        }

        // service / vprn * / interface * / ip-mtu
        leaf ip-mtu {
          tailf:info "Configure the interface IP MTU";
          tailf:cli-no-value-on-delete;
          type uint16;
        }

         // service / vprn * / interface * / loopback
        leaf loopback {
          type empty;
        }

        // service / vprn * / interface * / sap *
        list sap {
          tailf:info "Provision a SAP";
          tailf:cli-embed-no-on-delete;
          key sap-id;
          leaf sap-id {
            tailf:info "<sap-id>;;different formats depending on port mode";
            tailf:cli-diff-dependency "/alu:service/ies/interface/sap"
              + "[sap-id=current()/../sap-id]" {
              tailf:cli-trigger-on-set;
            }
            tailf:cli-diff-dependency "/alu:service/epipe/sap"
              + "[sap-id=current()/../sap-id]" {
              tailf:cli-trigger-on-set;
            }
            tailf:cli-diff-dependency "/alu:service/vpls/sap"
              + "[sap-id=current()/../sap-id]" {
              tailf:cli-trigger-on-set;
            }
            tailf:cli-diff-dependency "/alu:service/vprn/interface/sap"
              + "[sap-id=current()/../sap-id]" {
              tailf:cli-trigger-on-set;
            }
            type string;
          }

          // service / vprn * / interface * / sap * / create
          leaf create {
            tailf:cli-hide-in-submode;
            tailf:cli-no-name-on-delete;
            mandatory true;
            type empty;
          }

          // service / vprn * / interface * / sap * / accounting-policy
          leaf accounting-policy {
            tailf:cli-no-value-on-delete;
            type uint8 {
              range "1..99";
            }
          }

          // service / vprn * / interface * / sap * / anti-spoof
          leaf anti-spoof {
            tailf:info "Configures anti-spoof filtering for this SAP";
            tailf:cli-no-value-on-delete;
            type enumeration {
              enum ip;
              enum ip-mac;
              enum mac;
            }
          }

          // service / vprn * / interface * / sap * / collect-stats
          leaf collect-stats {
            tailf:info "Enable/disable statistics collection";
            type empty;
          }

          // service / vprn * / interface * / sap * / description
          leaf description {
            tailf:cli-no-value-on-delete;
            type string;
          }

          // service / vprn * / sap * / multi-service-site
          leaf multi-service-site {
            tailf:cli-no-value-on-delete;
            type leafref {
              path "/alu:service/customer/multi-service-site/"
                  +"customer-site-name";
            }
          }

          // service / vprn * / interface * / sap * / egress
          container egress {
            tailf:cli-add-mode;
            uses sap-egress-grouping;
          }

          // service / vprn * / interface * / sap * / eth-cfm
          container eth-cfm {
            tailf:cli-add-mode;
            uses eth-cfm;
          }

          // service / vprn * / interface * / sap * / ingress
          container ingress {
            tailf:cli-add-mode;
            uses sap-ingress-grouping;
          }

          // service / vprn * / interface * / sap * / ipsec-tunnel
          container ipsectunnel {
            tailf:cli-add-mode;
            uses sap-ingress-grouping;
          }

          // service / vprn * / interface * / sap * / lag-link-map-profile
          leaf lag-link-map-profile {
            tailf:cli-no-value-on-delete;
            type uint8 {
              range "1..32";
            }
          }

          // service / vprn * / interface * / sap * / shutdown
          leaf shutdown {
            tailf:info "Administratively enable/disable the vprn interface sap";
            tailf:cli-boolean-no;
            default true;
            type boolean;
          }
        }

        // service / vprn * / interface * / spoke-sdp
        list spoke-sdp {
          tailf:cli-embed-no-on-delete;
          tailf:info "<sdp-id>:<vc-id>";
          tailf:cli-key-format "$(1):$(2)";
          uses sdp-common;
          key "sdp-id vc-id";
        }

        // service / vprn * / interface * / urpf-check
        container urpf-check {
          tailf:cli-add-mode;

          leaf mode {
            tailf:cli-no-value-on-delete;
            type enumeration {
              enum strict;
              enum loose;
              enum strict-no-encap;
            }
          }
        }

        // service / vprn * / interface * / vpls *
        list vpls {
          tailf:info "Configure vpls service";
          key service-name;
          leaf service-name {
            type string;
          }

          // service / vprn * / interface * / vpls * / egress
          container egress {
            tailf:info "Configure vpls egress parameters";
            tailf:cli-add-mode;

            // service / vprn * / interface * / vpls * / egress
            // / reclassify-using-qos
            leaf reclassify-using-qos {
              tailf:info "Apply egress QoS policy";
              type string;
            }
          }
        }
        // service / vprn * / interface * / ipv6
        container ipv6 {
          tailf:cli-add-mode;
          tailf:info "Enables/Configures IPv6 for a VPRN interface";

          // service / vprn * / interface * / ipv6 / address
          leaf address {
            tailf:info "Assigns an IPv6 address to the VPRN interface.";
            type tailf:ipv6-address-and-prefix-length;
          }
        }
        // service / vprn * / interface * / shutdown
        leaf shutdown {
          tailf:info "Administratively enable/disable the vprn interface";
          tailf:cli-boolean-no;
          default true;
          type boolean;
        }
      }

      // service / vprn * / ipsec
      container ipsec {
        tailf:info "Configure IPsec Policies";
        tailf:cli-add-mode;

        // service / vprn * / ipsec / security-policy *
        list security-policy {
          tailf:info "Configure IPsec security policy";
          tailf:cli-embed-no-on-delete;
          key security-policy-id;
          leaf security-policy-id {
            type uint32;
          }

          // service / vprn * / ipsec / security-policy *
          list entry {
            tailf:info "Configure IPsec security policy params";
            tailf:cli-embed-no-on-delete;
            key entry-id;
            leaf entry-id {
              type uint8 {
                range "1..16";
              }
            }
            leaf local-ip {
              tailf:info "Configure local Ip prefix/mask for this policy "
                         + "param entry";
              tailf:cli-no-value-on-delete;
              type union {
                type enumeration {
                  enum "any";
                }
                type tailf:ipv4-address-and-prefix-length;
              }
            }

             leaf local-v6-ip {
               tailf:info "Configure local IPv6 prefix/mask for this policy "
                          + "param entry";
               tailf:cli-no-value-on-delete;
               type union {
                type enumeration {
                  enum "any";
                }
                type tailf:ipv6-address-and-prefix-length;
              }
             }

             leaf remote-ip {
               tailf:info "Configure remote Ip prefix/mask for this policy "
                         +"param entry";
               tailf:cli-no-value-on-delete;
               type union {
                type enumeration {
                  enum "any";
                }
                type tailf:ipv4-address-and-prefix-length;
              }
             }

             leaf remote-v6-ip {
               tailf:info "Configure remote IPv6 prefix/mask for this policy "
                         +"param entry";
               tailf:cli-no-value-on-delete;
               type union {
                type enumeration {
                  enum "any";
                }
                type tailf:ipv6-address-and-prefix-length;
              }
            }

            leaf create {
              tailf:cli-hide-in-submode;
              tailf:cli-no-name-on-delete;
              mandatory true;
              type empty;
            }
          }
        }
      }

      // service / vprn * / maximum-routes
      container maximum-routes {
        tailf:cli-embed-no-on-delete;
        tailf:cli-compact-syntax;

        leaf routes {
          tailf:cli-drop-node-name;
          tailf:cli-no-value-on-delete;
          type uint32;
        }
        leaf log-only {
          tailf:cli-no-value-on-delete;
          tailf:cli-no-name-on-delete;
          type empty;
        }
        leaf threshold {
          tailf:cli-no-value-on-delete;
          tailf:cli-no-name-on-delete;
          type uint8 {
            range "0..100";
          }
        }
      }

      // service / vprn * / route-distinguisher
      leaf route-distinguisher {
        tailf:info "[ip-address:number1 | asn:number2]";
        tailf:cli-no-value-on-delete;
        tailf:cli-no-name-on-delete;
        type string;
      }

      // service / vprn * / vrf-export
      leaf-list vrf-export {
        tailf:cli-flat-list-syntax;
        tailf:cli-no-value-on-delete;
        max-elements 15;
        type string;
      }

      // service / vprn * / vrf-import
      leaf-list vrf-import {
        tailf:cli-flat-list-syntax;
        tailf:cli-no-value-on-delete;
        max-elements 15;
        type string;
      }

      // service / vprn * / vrf-target
      container vrf-target {
        tailf:cli-embed-no-on-delete;
        choice vrf {
          leaf ext-community {
            tailf:cli-no-name-on-delete;
            type empty;
          }
          leaf export {
            tailf:cli-no-value-on-delete;
            tailf:cli-no-name-on-delete;
            type string;
          }
          leaf import {
            tailf:cli-no-value-on-delete;
            tailf:cli-no-name-on-delete;
            type string;
          }
          leaf ext-community-value{
            tailf:cli-drop-node-name;
            tailf:cli-no-value-on-delete;
            tailf:cli-no-name-on-delete;
            type string;
          }
        }
      }

      // service / vprn * / autonomous-system
      leaf autonomous-system {
        tailf:cli-no-value-on-delete;
        type uint32 {
          range "1..4294967295";
        }
      }

      // service / vprn * / spoke-sdp *
      list spoke-sdp {
        tailf:info "Configure spoke SDP bindings for VPRN services";
        key sdp-id;
        leaf sdp-id {
          type uint32;
          tailf:non-strict-leafref {
            path "/alu:service/sdp/sdp-id";
          }
        }
        // service / vprn * / spoke-sdp * create
        leaf create {
          mandatory true;
          type empty;
          tailf:cli-hide-in-submode;
          tailf:cli-no-name-on-delete;
        }
        // service / vprn * / spoke-sdp * description
        leaf description {
          tailf:cli-no-value-on-delete;
          tailf:info "Description for this SAA test";
          type string {
            length "1..80";
          }
        }
      }

      // service / vprn * / static-route *
      list static-route {
        tailf:info "Creates/deletes static route entries";
        tailf:cli-compact-syntax;
        tailf:cli-sequence-commands;
        tailf:cli-embed-no-on-delete;
        tailf:cli-suppress-mode;
        key route;
        leaf route {
          tailf:cli-drop-node-name;
          type union {
            type tailf:ipv4-address-and-prefix-length;
            type tailf:ipv6-address-and-prefix-length;
          }
        }

        choice nh {
          // service / vprn * / static-route * next-hop
          leaf next-hop {
            type union {
              type inet:ipv4-address;
              type inet:ipv6-address;
              type string;
            }
          }

          // service / vprn * / static-route * indirect
          leaf indirect {
            type inet:ipv4-address;
          }

          // service / vprn * / static-route * ipsec-tunnel
          leaf ipsec-tunnel {
            type string;
          }

          // service / vprn * / static-route * black-hole
          leaf black-hole {
            type empty;
          }
        }

        // service / vprn * / static-route * / preference
        leaf preference {
          tailf:cli-break-sequence-commands;
          type uint8 {
            range "1..255";
          }
        }

        // service / vprn * / static-route * / metric
        leaf metric {
          type uint16;
        }

        choice ed {
          // service / vprn * / static-route * / enable
          leaf enable {
            type empty;
          }

          // service / vprn * / static-route * / disable
          leaf disable {
            type empty;
          }
        }

        // service / vprn * / static-route * / tag
        leaf tag {
          type uint32 {
            range "1..4294967295";
          }
        }

        // service / vprn * / static-route * / bfd-enable
        leaf bfd-enable {
          tailf:info "enables BFD sessions on this static route";
          type empty;
        }

        // service / vprn * / static-route * / log
        leaf log {
          type empty;
        }

        // service / vprn * / static-route * / prefix-list-name
        leaf prefix-list-name {
          type string {
            length "1..32";
          }
        }

        choice an {
          // service / vprn * / static-route * / all
          leaf all {
            type empty;
          }

          // service / vprn * / static-route * / none
          leaf none {
            type empty;
          }
        }
      }

      // service / vprn * / sgt-qos
      container sgt-qos {
        tailf:info "Configure DSCP/Dot1p remarking for self-generated traffic";
        tailf:cli-add-mode;
        // service / vprn * / sgt-qos / application *
        list application {
          tailf:info "Configure DSCP/Dot1p re-marking for applications";
          tailf:cli-suppress-mode;
          key app-name;
          leaf app-name {
            type enumeration {
              enum bgp;
              enum pim;
              enum ospf;
              enum rip;
            }
          }

          // service / vprn * / sgt-qos / application * / dscp
          leaf dscp {
            tailf:info "Configure DSCP name to FC mapping";
            type string;
          }
        }
      }

      // service / vprn * / pim
      container pim {
        tailf:info "Create/Configure or delete PIM instance";
        tailf:cli-add-mode;

        // service / vprn * / pim / interface *
        list interface {
          tailf:info "Configure PIM interface";
          key name;
          leaf name {
            type string;
          }
        }
        // service / vprn * / pim / rp
        container rp {
          tailf:info "Configure the router as static or Candidate-RP";
          tailf:cli-add-mode;
          // service / vprn * / pim / rp / static
          container static {
            tailf:info "Context to configure static group to RP mapping";
            tailf:cli-add-mode;
            presence true;
            // service / vprn * / pim / rp / static / address *
            list address {
              tailf:info "Configure the RP address for mcast group prefixes";
              key address;
              leaf address{
                type union {
                  type inet:ipv4-address;
                  type inet:ipv6-address;
                }
              }
              // service / vprn * / pim / rp / static / address * / group-prefix
              list group-prefix {
                tailf:info "Configure a group prefix for the RP address";
                tailf:cli-suppress-mode;
                key address;
                leaf address {
                  type tailf:ipv4-address-and-prefix-length;
                }
              }
              // service / vprn * / pim / rp / static / address * / override
              leaf override {
                tailf:info "Change the precedence of static RP over "+
                  "dynamically learnt RP";
                type empty;
              }
            }
          }
          // service / vprn * / pim / rp / bsr-candidate
          container bsr-candidate {
            tailf:info "Context to configure Candidate Bootstrap parameters";
            tailf:cli-add-mode;
            leaf shutdown {
              tailf:cli-boolean-no;
              default true;
              type boolean;
            }
          }
          // service / vprn * / pim / rp / rp-candidate
          container rp-candidate {
            tailf:info "Context to configure the Candidate RP parameters";
            tailf:cli-add-mode;
            leaf shutdown {
              tailf:cli-boolean-no;
              default true;
              type boolean;
            }
          }
        }
      }
      // service / vprn * / mvpn
      container mvpn {
        tailf:info "Configure multicast VPN";
        tailf:cli-add-mode;

        // service / vprn * / mvpn / auto-discovery
        leaf auto-discovery {
          tailf:info "Enable/disable multicast VPN membership auto-discovery";
          type enumeration {
            enum default;
            enum mdt-safi;
          }
        }

        // service / vprn * / mvpn / c-mcast-signaling
        leaf c-mcast-signaling {
          tailf:info "Specifies the protocol to use for PE-to-PE signaling";
          type enumeration {
            enum bgp;
            enum pim;
          }
        }

        // service / vprn * / mvpn / provider-tunnel
        container provider-tunnel {
          tailf:info "Configure provider tunnel for the multicast VPN";
          tailf:cli-add-mode;

          // service / vprn * / mvpn / provider-tunnel / inclusive
          container inclusive {
            tailf:info "Configure inclusive provider tunnel for the mcast VPN";
            tailf:cli-add-mode;

            // service / vprn * / mvpn / provider-tunnel / inclusive / pim
            container pim {
              tailf:info "Configure the PIM mode and group address for PIM "+
                "based inclusive provider tunnels";
              tailf:cli-add-mode;
              presence present;
              // service / vprn * / mvpn / provider-tunnel / inclusive / pim /
              // multicast-type
              leaf multicast-type {
                tailf:cli-drop-node-name;
                type enumeration {
                  enum asm;
                  enum ssm;
                }
              }
              // service / vprn * / mvpn / provider-tunnel / inclusive / pim /
              // grp-ip-address
               leaf grp-ip-address{
                tailf:cli-drop-node-name;
                type inet:ipv4-address;
              }
              // service / vprn * / mvpn / provider-tunnel / inclusive /
              // pim / shutdown
              leaf shutdown {
                tailf:cli-boolean-no;
                default true;
                type boolean;
              }
            }

            // service / vprn * / mvpn / provider-tunnel / inclusive / rsvp
            container rsvp {
              tailf:info "Enable/Disable the Context for specifiying"
                        +" RSVP P2MP LSP for the provider tunnel";
              tailf:cli-add-mode;
              // service / vprn * / mvpn / provider-tunnel / inclusive /
              // rsvp / lsp-template
              leaf lsp-template {
                type string;
              }
              // service / vprn * / mvpn / provider-tunnel / inclusive /
              // rsvp / shutdown
              leaf shutdown {
                tailf:cli-boolean-no;
                default true;
                type boolean;
              }
            }
          }
        }

        // service / vprn * / mvpn / vrf-target *
        list vrf-target {
          tailf:info "Route target to be used for the multicast VPN";
          key id;
          leaf id {
            type string;
          }

          // service / vprn * / mvpn / vrf-target * / export
          leaf export {
            tailf:info "Specifies communitities to be sent to peers";
            type string;
          }

          // service / vprn * / mvpn / vrf-target * / import
          leaf import {
            tailf:info "Specifies communitities to be accepted from peers";
            type string;
          }
        }
      }


      // service / vprn * / router-id
      leaf router-id {
        tailf:info "Configure the router-id for the virtual router";
        type inet:ipv4-address;
      }

      // Best effort implementation of isis, since this list is not
      // available on our test devices.

      // service / vprn * / isis *
      list isis {
        key id;
        leaf id {
          type uint32;
        }
        // service / vprn * / isis * / area-id
        leaf area-id {
          type string;
        }
        // service / vprn * / isis * / ipv6-routing
        leaf ipv6-routing {
          type enumeration {
            enum native;
            enum mt;
          }
        }
        // service / vprn * / isis * / multi-topology
        container multi-topology {
          tailf:cli-add-mode;

          leaf ipv6-unicast {
            type empty;
          }
        }
        // service / vprn * / isis * / interface *
        list interface {
          key name;
          leaf name {
            type string;
          }
          // service / vprn * / isis * / interface * / passive
          leaf passive {
            type empty;
          }
          // service / vprn * / isis * / interface * / interface-type
          leaf interface-type {
            type enumeration {
              enum point-to-point;
            }
          }
          // service / vprn * / isis * / interface * / shutdown
          leaf shutdown {
            tailf:cli-boolean-no;
            default true;
            type boolean;
          }
        }
        // service / vprn * / isis * / router-id
        leaf router-id {
          type inet:ipv4-address;
        }
        // service / vprn * / isis * / router-id
        leaf shutdown {
          tailf:cli-boolean-no;
          default true;
          type boolean;
        }
      }

      // service / vprn * / create
      leaf create {
        tailf:cli-hide-in-submode;
        tailf:cli-no-name-on-delete;
        mandatory true;
        type empty;
      }

      // service / vprn * / shutdown
      leaf shutdown {
        tailf:info "Administratively enable/disable the service";
        tailf:cli-boolean-no;
        default true;
        type boolean;
      }
    }

    // service / pw-template *
    list pw-template {
      tailf:info "Configure a pseudowire template policy";
      tailf:cli-embed-no-on-delete;
      key policy-id;
      leaf policy-id {
        type uint16;
      }

      // service / pw-template * / use-provisioned-sdp
      leaf use-provisioned-sdp {
        tailf:cli-hide-in-submode;
        tailf:cli-no-name-on-delete;
        type empty;
      }

      // service / pw-template * / create
      leaf create {
        tailf:cli-hide-in-submode;
        tailf:cli-no-name-on-delete;
        mandatory true;
        type empty;
      }

      // service / pw-template * / force-vlan-vc-forwarding
      leaf force-vlan-vc-forwarding{
        tailf:info "Forces vlan-vc-type forwarding in the data-path";
        type empty;
      }

      // service / pw-template * / split-horizon-group *
      list split-horizon-group {
        tailf:cli-embed-no-on-delete;
        tailf:info "Configure a split horizon group";
        key group-name;
        leaf group-name {
          tailf:info "<group-name>;;<32 chars max>";
          type string {
            length "1..32";
          }
        }

        // service / pw-template * / split-horizon-group * /
        // auto-learn-mac-protect
        leaf auto-learn-mac-protect {
          tailf:info "Enable/disable automatic update of MAC protect list";
          type empty;
        }

        // service / pw-template * / split-horizon-group * / description
        leaf description {
          tailf:info "Description for this group";
          tailf:cli-no-value-on-delete;
          type string;
        }

        // service / pw-template * / split-horizon-group * /
        // restrict-protected-src
        container restrict-protected-src {
          tailf:info "Enable/disable protected src MAC restriction";
          tailf:cli-embed-no-on-delete;
          presence true;
          leaf option {
            tailf:cli-drop-node-name;
            tailf:cli-no-value-on-delete;
            tailf:cli-delete-container-on-delete;
            type enumeration {
              enum alarm-only;
              enum discard-frame;
            }
          }
        }

        // service / pw-template * / split-horizon-group * /
        // restrict-unprotected-dst
        leaf restrict-unprotected-dst {
          tailf:info "Enable/disable unprotected dst MAC restriction";
          type empty;
        }
      }

      // service / pw-template * / vc-type
      leaf vc-type {
        tailf:info "Configure VC type";
        tailf:cli-no-name-on-delete;
        tailf:cli-no-value-on-delete;
        default ether;
        type enumeration {
          enum ether;
          enum vlan;
        }
      }
    }
  }


  /// ========================================================================
  /// router *
  /// ========================================================================
  list router {
    tailf:info "Configure router instance";
    tailf:cli-recursive-delete;
    tailf:cli-embed-no-on-delete;
    key router-name;
    leaf router-name {
      type string;
    }

    // router * / autonomous-system
    leaf autonomous-system {
      tailf:cli-no-value-on-delete;
      type uint32;
    }

    // router * / bgp /
    container bgp {
      tailf:info "Create/Configure or delete BGP instance";
      tailf:cli-add-mode;
      tailf:cli-embed-no-on-delete;
      presence present;

      // router * / bgp / add-paths /
      container add-paths {
        tailf:info "Enable/Disable BGP ADD-PATHS";
        tailf:cli-add-mode;
        tailf:cli-embed-no-on-delete;

        // router * / bgp / add-paths / ipv4
        container ipv4 {
          tailf:info "Configure ipv4 ADD-PATH limits";
          tailf:cli-embed-no-on-delete;
          tailf:cli-compact-syntax;
          tailf:cli-sequence-commands;

          leaf send {
            tailf:cli-no-name-on-delete;
            tailf:cli-no-value-on-delete;
            type union {
              type uint8 {
                range "1..16";
              }
              type enumeration {
                enum none;
              }
            }
          }

          leaf receive {
            tailf:cli-no-name-on-delete;
            tailf:cli-no-value-on-delete;
            type enumeration {
              enum none;
            }
          }
        }

        // router * / bgp / add-paths / ipv6
        container ipv6 {
          tailf:info "Configure ipv6 ADD-PATH limits";
          tailf:cli-embed-no-on-delete;
          tailf:cli-compact-syntax;
          tailf:cli-sequence-commands;

          leaf send {
            tailf:cli-no-name-on-delete;
            tailf:cli-no-value-on-delete;
            type union {
              type uint8 {
                range "1..16";
              }
              type enumeration {
                enum none;
              }
            }
          }

          leaf receive {
            tailf:cli-no-name-on-delete;
            tailf:cli-no-value-on-delete;
            type enumeration {
              enum none;
            }
          }

        }

        // router * / bgp / add-paths / vpn-ipv4
        container vpn-ipv4 {
          tailf:info "Configure vpn-ipv4 ADD-PATH limits";
          tailf:cli-embed-no-on-delete;
          tailf:cli-compact-syntax;
          tailf:cli-sequence-commands;

          leaf send {
            tailf:cli-no-name-on-delete;
            tailf:cli-no-value-on-delete;
            type union {
              type uint8 {
                range "1..16";
              }
              type enumeration {
                enum none;
              }
            }
          }

          leaf receive {
            tailf:cli-no-name-on-delete;
            tailf:cli-no-value-on-delete;
            type enumeration {
              enum none;
            }
          }

        }

        // router * / bgp / add-paths / vpn-ipv6
        container vpn-ipv6 {
          tailf:info "Configure vpn-ipv6 ADD-PATH limits";
          tailf:cli-embed-no-on-delete;
          tailf:cli-compact-syntax;
          tailf:cli-sequence-commands;

          leaf send {
            tailf:cli-no-name-on-delete;
            tailf:cli-no-value-on-delete;
            type union {
              type uint8 {
                range "1..16";
              }
              type enumeration {
                enum none;
              }
            }
          }

          leaf receive {
            tailf:cli-no-name-on-delete;
            tailf:cli-no-value-on-delete;
            type enumeration {
              enum none;
            }
          }

        }
      }

      // router * / bgp / advertise-external
      leaf-list advertise-external {
        tailf:info "Enable/Disable Advertise Best External for the bgp family";
        tailf:cli-flat-list-syntax;
        type enumeration {
          enum ipv4;
          enum ipv6;
        }
      }

      // router * / bgp / advertise-inactive
      leaf advertise-inactive {
        tailf:info "Enable/disable advertising of inactive BGP routes"
          + " to other BGP peers";
        type empty;
      }

      // router * / bgp /
      leaf aggregator-id-zero {
        tailf:info "Enable/disable setting the router ID to 0 in"
          + " the aggregator";
        type empty;
      }

      // router * / bgp / auth-keychain
      leaf auth-keychain {
        tailf:info "Configure TCP authentication keychain to use"
          + " for the session";
        tailf:cli-no-value-on-delete;
        type string;
      }

      // router * / bgp / authentication-key
      container authentication-key {
        tailf:info "Configure the BGP authentication key for all peers";
        tailf:cli-embed-no-on-delete;
        tailf:cli-compact-syntax;
        tailf:cli-sequence-commands;

        leaf key {
          tailf:cli-drop-node-name;
          tailf:cli-no-value-on-delete;
          type string;
        }

        leaf type {
          tailf:cli-drop-node-name;
          tailf:cli-no-value-on-delete;
          type enumeration {
            enum hash;
            enum hash2;
          }
        }
      }

      // router * / bgp / backup-path
      leaf-list backup-path {
        tailf:info "Enable/Disable Backup Path for the bgp family";
        tailf:cli-flat-list-syntax;
        type enumeration {
          enum ipv4;
          enum ipv6;
        }
      }

      // router * / bgp / best-path-selection /
      container best-path-selection {
        tailf:info "Enable/Disable Path Selection Config";
        tailf:cli-add-mode;

        // router * / bgp / best-path-selection / always-compare-med
        container always-compare-med {
          tailf:info "Determine how the Multi-Exit Discriminator (MED)";
          tailf:cli-compact-syntax;
          tailf:cli-embed-no-on-delete;

          leaf strict-as {
            tailf:cli-no-name-on-delete;
            type empty;
          }

          leaf type {
            tailf:cli-no-value-on-delete;
            tailf:cli-no-name-on-delete;
            type enumeration {
              enum zero;
              enum infinity;
            }
          }
        }

        // router * / bgp / best-path-selection / as-path-ignore
        leaf-list as-path-ignore {
          tailf:info "Determine whether the AS Path is used";
          tailf:cli-flat-list-syntax;
          tailf:cli-no-value-on-delete;
          type enumeration {
            enum ipv4;
            enum ipv6;
            enum vpn-ipv4;
            enum vpn-ipv6;
            enum mcast-ipv4;
            enum mvpn-ipv4;
            enum l2-vpn;
            enum mvpn-ipv6;
          }
        }

        // router * / bgp / best-path-selection / deterministic-med
        leaf deterministic-med {
          tailf:info "Enable/Disable deterministic MED";
          type empty;
        }

        // router * / bgp / best-path-selection / ignore-nh-metric
        leaf ignore-nh-metric {
          tailf:info "Enable/Disable ignore next-hop metric";
          type empty;
        }

        // router * / bgp / best-path-selection / ignore-router-id
        leaf ignore-router-id {
          tailf:info "Enable/Disable ignore router-id";
          type empty;
        }
      }

      // router * / bgp / bfd-enable
      leaf bfd-enable {
        tailf:info "Enable BFD";
        type empty;
      }

      // router * / bgp / cluster
      leaf cluster {
        tailf:info "Configure the cluster ID for a route reflector server";
        tailf:cli-no-value-on-delete;
        type inet:ipv4-address;
      }

      // router * / bgp / connect-retry
      leaf connect-retry {
        tailf:info "Configure the BGP Connect Retry timer value";
        tailf:cli-no-value-on-delete;
        type uint16 {
          range "1..65535";
        }
      }

      // router * / bgp / damping
      leaf damping {
        tailf:info "Enable/disable BGP route damping for learned routes";
        type empty;
      }

      // router * / bgp / description
      leaf description {
        tailf:info "Create a textual description stored in the"
          + " configuration file";
        tailf:cli-no-value-on-delete;
        type string;
      }

      // router * / bgp / disable-4byte-asn
      leaf disable-4byte-asn {
        tailf:info "Enable/disable the advertisement of 4-byte ASN";
        type empty;
      }

      // router * / bgp / disable-client-reflect
      leaf disable-client-reflect {
        tailf:info "Enable/disable the reflection of routes by the "
          + " route reflector at the global level";
        type empty;
      }

      // router * / bgp / disable-communities
      leaf-list disable-communities {
        tailf:info "Configure BGP to disable sending communities";
        tailf:cli-no-value-on-delete;
        tailf:cli-flat-list-syntax;
        type enumeration {
          enum standard;
          enum extended;
        }
      }

      // router * / bgp / disable-fast-external-failover
      leaf disable-fast-external-failover {
        tailf:info "Configure BGP fast external failover";
        type empty;

      }

      // router * / bgp / disable-route-table-install
      leaf disable-route-table-install {
        tailf:info "Enable/Disable route table installation";
        type empty;
      }

      // router * / bgp / enable-inter-as-vpn
      leaf enable-inter-as-vpn {
        tailf:info "Configure BGP to enable sending VPN routes across AS";
        type empty;
      }

      // router * / bgp / enable-peer-tracking
      leaf enable-peer-tracking {
        tailf:info "Enable/disable BGP peer tracking";
        type empty;
      }

      // router * / bgp / enable-rr-vpn-forwarding
      leaf enable-rr-vpn-forwarding {
        tailf:info "Configure BGP to enable route-reflector";
        type empty;
      }

      // router * / bgp / export
      leaf-list export {
        tailf:info "Export route policies used";
        tailf:cli-flat-list-syntax;
        tailf:cli-no-value-on-delete;
        type string;
      }

      // router * / bgp / family
      leaf-list family {
        tailf:info "Configure the IP family capability";
        tailf:cli-flat-list-syntax;
        tailf:cli-no-value-on-delete;
        type enumeration {
          enum ipv4;
          enum vpn-ipv4;
          enum ipv6;
          enum vpn-ipv6;
          enum mcast-ipv4;
          enum l2-vpn;
          enum mvpn-ipv4;
          enum mdt-safi;
          enum ms-pw;
          enum flow-ipv4;
          enum route-target;
          enum mcast-vpn-ipv4;
          enum mvpn-ipv6;
          enum flow-ipv6;
        }
      }

      // router * / bgp / flowspec-validate
      leaf flowspec-validate {
        tailf:info "Enable/Disable Flowspec Validation";
        type empty;
      }

      // router * / bgp / graceful-restart /
      container graceful-restart {
        tailf:info "Enable/disable graceful-restart for all BGP peers";
        tailf:cli-add-mode;
        tailf:cli-embed-no-on-delete;

        // router * / bgp / graceful-restart / stale-routes-time
        leaf stale-routes-time {
          tailf:cli-no-value-on-delete;
          tailf:cli-no-name-on-delete;
          type uint16 {
            range "1..3600";
          }
        }
      }

      // router * / bgp / group *
      list group {
        tailf:info "Configure a BGP group";
        tailf:cli-embed-no-on-delete;
        key id;
        leaf id {
          type string;
        }

        // router * / bgp / group * / add-paths /
        container add-paths  {
          tailf:info "Enable/Disable BGP ADD-PATHS for the group";
          tailf:cli-add-mode;
          tailf:cli-embed-no-on-delete;

          // router * / bgp / group * / add-paths / ipv4
          container ipv4 {
            tailf:info "Configure ipv4 ADD-PATH limits";
            tailf:cli-embed-no-on-delete;
            tailf:cli-compact-syntax;
            tailf:cli-sequence-commands;

            leaf send {
              tailf:cli-no-name-on-delete;
              tailf:cli-no-value-on-delete;
              type union {
                type uint8 {
                  range "1..16";
                }
                type enumeration {
                  enum none;
                }
              }
            }

            leaf receive {
              tailf:cli-no-name-on-delete;
              tailf:cli-no-value-on-delete;
              type enumeration {
                enum none;
              }
            }
          }

          // router * / bgp / group * / add-paths / ipv6
          container ipv6 {
            tailf:info "Configure ipv6 ADD-PATH limits";
            tailf:cli-embed-no-on-delete;
            tailf:cli-compact-syntax;
            tailf:cli-sequence-commands;

            leaf send {
              tailf:cli-no-name-on-delete;
              tailf:cli-no-value-on-delete;
              type union {
                type uint8 {
                  range "1..16";
                }
                type enumeration {
                  enum none;
                }
              }
            }

            leaf receive {
              tailf:cli-no-name-on-delete;
              tailf:cli-no-value-on-delete;
              type enumeration {
                enum none;
              }
            }

          }

          // router * / bgp / group * / add-paths / vpn-ipv4
          container vpn-ipv4 {
            tailf:info "Configure vpn-ipv4 ADD-PATH limits";
            tailf:cli-embed-no-on-delete;
            tailf:cli-compact-syntax;
            tailf:cli-sequence-commands;

            leaf send {
              tailf:cli-no-name-on-delete;
              tailf:cli-no-value-on-delete;
              type union {
                type uint8 {
                  range "1..16";
                }
                type enumeration {
                  enum none;
                }
              }
            }

            leaf receive {
              tailf:cli-no-name-on-delete;
              tailf:cli-no-value-on-delete;
              type enumeration {
                enum none;
              }
            }

          }

          // router * / bgp / group * / add-paths / vpn-ipv6
          container vpn-ipv6 {
            tailf:info "Configure vpn-ipv6 ADD-PATH limits";
            tailf:cli-embed-no-on-delete;
            tailf:cli-compact-syntax;
            tailf:cli-sequence-commands;

            leaf send {
              tailf:cli-no-name-on-delete;
              tailf:cli-no-value-on-delete;
              type union {
                type uint8 {
                  range "1..16";
                }
                type enumeration {
                  enum none;
                }
              }
            }

            leaf receive {
              tailf:cli-no-name-on-delete;
              tailf:cli-no-value-on-delete;
              type enumeration {
                enum none;
              }
            }

          }
        }

        // router * / bgp / group * / advertise-inactive
        leaf advertise-inactive {
          tailf:info "Enable/disable advertising of inactive BGP routes";
          type empty;
        }

        // router * / bgp / group * / aggregator-id-zero
        leaf aggregator-id-zero {
          tailf:info "Enable/disable (group level) setting the router ID";
          type empty;
        }

        // router * / bgp / group * / aigp
        leaf aigp {
          tailf:info "Enable/Disable AIGP";
          type empty;
        }

        // router * / bgp / group * / auth-keychain
        leaf auth-keychain   {
          tailf:info "Configure TCP authentication keychain to use";
          tailf:cli-no-value-on-delete;
          type string;
        }

        // router * / bgp / group * / authentication-key
        container authentication-key {
          tailf:info "Configure the BGP authentication key for the group";
          tailf:cli-embed-no-on-delete;
          tailf:cli-compact-syntax;
          tailf:cli-sequence-commands;

          leaf key {
            tailf:cli-drop-node-name;
            tailf:cli-no-value-on-delete;
            type string;
          }

          leaf type {
            tailf:cli-drop-node-name;
            tailf:cli-no-value-on-delete;
            type enumeration {
              enum hash;
              enum hash2;
            }
          }
        }


        // router * / bgp / group * / bfd-enable
        leaf bfd-enable      {
          tailf:info "Enable BFD";
          type empty;
        }

        // router * / bgp / group * / cluster
        leaf cluster         {
          tailf:info "Configure the cluster ID for a route reflector";
          tailf:cli-no-value-on-delete;
          type inet:ipv4-address;
        }

        // router * / bgp / group * / connect-retry
        leaf connect-retry   {
          tailf:info "Configure the BGP Connect Retry timer value";
          tailf:cli-no-value-on-delete;
          type uint16 {
            range "1..65535";
          }
        }

        // router * / bgp / group * / damping
        leaf damping         {
          tailf:info "Enable/disable (group level) BGP route damping";
          type empty;
        }

        // router * / bgp / group * / default-route-target
        leaf default-route-target {
          tailf:info "Configure BGP group default route target";
          type empty;
        }

        // router * / bgp / group * / description
        leaf description     {
          tailf:info "Create a textual description for the group";
          tailf:cli-no-value-on-delete;
          type string;
        }

        // router * / bgp / group * / disable-4byte-asn
        leaf disable-4byte-asn {
          tailf:info "Enable/disable the advertisement of 4-byte ASN";
          type empty;
        }

        // router * / bgp / group * / disable-capability-negotiation
        leaf disable-capability-negotiation {
          tailf:info "Configure BGP group capability negotiation";
          type empty;
        }

        // router * / bgp / group * / disable-client-reflect
        leaf disable-client-reflect {
          tailf:info "Enable/disable the reflection of routes";
          type empty;
        }

        // router * / bgp / group * / disable-communities
        leaf-list disable-communities {
          tailf:info "Configure BGP to disable sending communities";
          tailf:cli-no-value-on-delete;
          tailf:cli-flat-list-syntax;
          type enumeration {
            enum standard;
            enum extenden;
          }
        }

        // router * / bgp / group * / disable-fast-external-failover
        leaf disable-fast-external-failover {
          tailf:info "Configure BGP fast external failover";
          type empty;
        }

        // router * / bgp / group * / enable-peer-tracking
        leaf enable-peer-tracking {
          tailf:info "Enable/disable BGP peer tracking";
          type empty;
        }

        // router * / bgp / group * / export
        leaf-list export {
          tailf:info "Export route policies used to determine routes";
          tailf:cli-no-value-on-delete;
          tailf:cli-flat-list-syntax;
          tailf:non-strict-leafref {
              path "/alu:router/policy-options/begin/policy-statement/name";
          }
          type string;
        }

        // router * / bgp / group * / family
        leaf-list family {
          tailf:info "Configure the IP family capability";
          tailf:cli-flat-list-syntax;
          tailf:cli-no-value-on-delete;
          type enumeration {
            enum ipv4;
            enum vpn-ipv4;
            enum ipv6;
            enum vpn-ipv6;
            enum mcast-ipv4;
            enum l2-vpn;
            enum mvpn-ipv4;
            enum mdt-safi;
            enum ms-pw;
            enum flow-ipv4;
            enum route-target;
            enum mcast-vpn-ipv4;
            enum mvpn-ipv6;
            enum flow-ipv6;
          }
        }

        // router * / bgp / group * / flowspec-validate
        leaf flowspec-validate {
          tailf:info "Enable/Disable Flowspec Validation";
          type empty;
        }

        // router * / bgp / group * / graceful-restart
        container graceful-restart {
          tailf:info "Enable/disable graceful-restart for BGP peer group";
          tailf:cli-add-mode;
          tailf:cli-embed-no-on-delete;

          // router * / bgp / group * / graceful-restart / stale-routes-time
          leaf stale-routes-time {
            tailf:cli-no-value-on-delete;
            tailf:cli-no-name-on-delete;
            type uint16 {
              range "1..3600";
            }
          }
        }

        // router * / bgp / group * / hold-time
        container hold-time       {
          tailf:info "Configure BGP hold time";
          tailf:cli-compact-syntax;

          leaf seconds {
            tailf:cli-drop-node-name;
            tailf:cli-no-value-on-delete;
            type uint16 {
              range "3..65535";
            }
          }

          leaf min {
            tailf:cli-no-value-on-delete;
            tailf:cli-no-name-on-delete;
            type uint16 {
              range "3..65535";
            }
          }
        }

        // router * / bgp / group * / import
        leaf-list import {
          tailf:info "Import route policies used to determine routes";
          tailf:cli-no-value-on-delete;
          tailf:cli-flat-list-syntax;
          type string;
        }

        // router * / bgp / group * / keepalive
        leaf keepalive {
          tailf:info "Configure BGP keepalive timer for the group";
          tailf:cli-no-value-on-delete;
          type uint16 {
            range "0..21845";
          }
        }

        // router * / bgp / group * / local-address
        leaf local-address {
          tailf:info "Local IP address used by the group";
          tailf:cli-no-value-on-delete;
          type union {
            type inet:ipv4-address;
            type inet:ipv6-address;
          }
        }

        // router * / bgp / group * / local-as
        container local-as {
          tailf:info "Add/remove a BGP virtual AS number";
          tailf:cli-embed-no-on-delete;
          tailf:cli-compact-syntax;
          tailf:cli-sequence-commands;

          leaf number {
            tailf:cli-no-value-on-delete;
            tailf:cli-no-name-on-delete;
            type uint32;
          }

          leaf private {
            tailf:cli-no-name-on-delete;
            type empty;
          }

          leaf no-prepend-global-as {
            tailf:cli-no-name-on-delete;
            type empty;
          }
        }

        // router * / bgp / group * / local-preference
        leaf local-preference {
          tailf:info "Configure BGP local-preference attribute";
          tailf:cli-no-value-on-delete;
          type uint32;
        }

        // router * / bgp / group * / loop-detect
        leaf loop-detect {
          tailf:info "Configure (group level) how the BGP peer session";
          tailf:cli-no-value-on-delete;
          type enumeration {
            enum drop-peer;
            enum discard-route;
            enum ignore-loop;
            enum off;
          }
        }

        // router * / bgp / group * / med-out
        leaf med-out         {
          tailf:info "Enable/disable (group level) advertising the MED";
          tailf:cli-no-value-on-delete;
          type union {
            type uint32;
            type enumeration {
              enum igp-cost;
            }
          }
        }

        // router * / bgp / group * / min-as-origination
        leaf min-as-origination {
          tailf:info "Minimum interval (group level) at which a given path";
          tailf:cli-no-value-on-delete;
          type uint8 {
            range "2..255";
          }
        }

        // router * / bgp / group * / min-route-advertisement
        leaf min-route-advertisement {
          tailf:info "Minimum interval (group level) at which a prefix";
          tailf:cli-no-value-on-delete;
          type uint8 {
            range "2..255";
          }
        }

        // router * / bgp / group * / multihop
        leaf multihop {
          tailf:info "TTL value (group level) entered in the IP header";
          tailf:cli-no-value-on-delete;
          type uint8 {
            range "1..255";
          }
        }

        // router * / bgp / group * / neighbor *
        list neighbor {
          tailf:info "Configure a neighbor for this group";
          tailf:cli-embed-no-on-delete;
          key address;
          leaf address {
            type union {
              type inet:ipv4-address;
              type inet:ipv6-address;
            }
          }

          // router * / bgp / group / neighbor * / description
          leaf description {
            tailf:info "Create a textual description for the neighbor";
            tailf:cli-no-value-on-delete;
            type string;
          }

          // router * / bgp / group / neighbor * / authentication-key
          container authentication-key {
            tailf:info "Configure the BGP authentication key for the peer";
            tailf:cli-embed-no-on-delete;
            tailf:cli-compact-syntax;
            tailf:cli-sequence-commands;

            leaf key {
              tailf:cli-drop-node-name;
              tailf:cli-no-value-on-delete;
              type string;
            }

            leaf hash {
              tailf:cli-drop-node-name;
              tailf:cli-no-value-on-delete;
              type enumeration {
                enum hash;
                enum hash2;
              }
            }
          }

          // router * / bgp / group * / neighbor * / peer-as
          leaf peer-as {
            tailf:info "Configure (group level) the AS number";
            tailf:cli-no-value-on-delete;
            type uint32;
          }

          // router * / bgp / group * / neighbor * / remove-private
          container remove-private  {
            tailf:info "Remove private AS numbers from the AS Path";
            presence true;
            leaf-list options {
              tailf:cli-drop-node-name;
              tailf:cli-flat-list-syntax;
              tailf:cli-no-value-on-delete;
              type enumeration {
                 enum limited;
                 enum skip-peer-as;
              }
            }
          }

          // router * / bgp / group / neighbor * / shutdown
          leaf shutdown {
            tailf:info "Administratively enable/disable the BGP neighbor";
            tailf:cli-boolean-no;
            default true;
            type boolean;
          }
        }

        // router * / bgp / group / next-hop-self
        leaf next-hop-self   {
          tailf:info "Configure the group to always set the nexthop path";
          type empty;
        }

        // router * / bgp / group / outbound-route-filtering
        container outbound-route-filtering {
          tailf:info "Enable/disable outbound route filtering for this";
          tailf:cli-add-mode;

          // router * / bgp / group / outbound-route-filtering /
          // extended-community
          container extended-community {
            tailf:info "Enable/disable outbound route filtering"
              + " using extended communities";
            tailf:cli-add-mode;

            // router * / bgp / group / outbound-route-filtering /
            // extended-community / accept-orf
            leaf accept-orf {
              tailf:info "Enable/disable acceptance of ORFs";
              type empty;
            }

            // router * / bgp / group / outbound-route-filtering /
            // extended-community / send-orf
            leaf-list send-orf {
              tailf:info "Add/Remove members to the send ORF list";
              tailf:cli-no-value-on-delete;
              tailf:cli-flat-list-syntax;
              type union {
                type uint32;
                type inet:ipv4-address;
              }
            }
          }
        }

        // router * / bgp / group / passive
        leaf passive {
          tailf:info "Enable/disable passive mode for the BGP group";
          type empty;
        }

        // router * / bgp / group / path-mtu-discovery
        leaf path-mtu-discovery {
          tailf:info "Enable/Disable Path MTU Discovery";
          type empty;
        }

        // router * / bgp / group / peer-as
        leaf peer-as {
          tailf:info "Configure (group level) the AS number";
          tailf:cli-no-value-on-delete;
          type uint32;
        }

        // router * / bgp / group / preference
        leaf preference  {
          tailf:info "Configure the route preference for routes";
          tailf:cli-no-value-on-delete;
          type uint8 {
            range "1..255";
          }
        }

        // router * / bgp / group / prefix-limit
        container prefix-limit {
          tailf:info "Maximum number of routes BGP can learn";
          tailf:cli-embed-no-on-delete;
          tailf:cli-compact-syntax;
          tailf:cli-sequence-commands;

          leaf limit {
            tailf:cli-drop-node-name;
            tailf:cli-no-value-on-delete;
            type uint32;
          }

          leaf log-only {
            tailf:cli-no-name-on-delete;
            type empty;
          }

          leaf treshold {
            tailf:cli-no-name-on-delete;
            tailf:cli-no-value-on-delete;
            type uint8 {
              range "1..100";
            }
          }

          leaf idle-timeout {
            tailf:cli-no-name-on-delete;
            tailf:cli-no-value-on-delete;
            type union {
              type uint16 {
                range "0..1024";
              }
              type enumeration {
                enum forever;
              }
            }
          }
        }

        // router * / bgp / group / remove-private
        container remove-private  {
          tailf:info "Remove private AS numbers from the AS Path";
          presence true;
          leaf-list options {
            tailf:cli-drop-node-name;
            tailf:cli-flat-list-syntax;
            tailf:cli-no-value-on-delete;
            type enumeration {
               enum limited;
               enum skip-peer-as;
            }
          }
        }

        // router * / bgp / group / split-horizon
        leaf split-horizon   {
          tailf:info "Configure split horizon for the peers under this";
          type empty;
        }

        // router * / bgp / group / ttl-security
        leaf ttl-security    {
          tailf:info "Configure TTL security parameters for incoming";
          tailf:cli-no-value-on-delete;
          type uint8 {
            range "1..255";
          }
        }

        // router * / bgp / group / type
        leaf type            {
          tailf:info "Configure the peers for this group";
          tailf:cli-no-value-on-delete;
          type enumeration {
            enum internal;
            enum external;
          }
        }

        // router * / bgp / group / vpn-apply-export
        leaf vpn-apply-export {
          tailf:info "Enable/disable BGP VPN export policy";
          type empty;
        }

        // router * / bgp / group / vpn-apply-import
        leaf vpn-apply-import {
          tailf:info "Enable/disable BGP VPN import policy";
          type empty;
        }

        // router * / bgp / group / shutdown
        leaf shutdown        {
          tailf:info "Administratively enable/disable the BGP group";
          tailf:cli-boolean-no;
          default true;
          type boolean;
        }
      }

      // router * / bgp /   hold-time
      container hold-time {
        tailf:info "Configure BGP hold time";
        tailf:cli-compact-syntax;

        leaf seconds {
          tailf:cli-drop-node-name;
          tailf:cli-no-value-on-delete;
          type uint16 {
            range "3..65535";
          }
        }

        leaf min {
          tailf:cli-no-value-on-delete;
          tailf:cli-no-name-on-delete;
          type uint16 {
            range "3..65535";
          }
        }
      }

      // router * / bgp /
      leaf ibgp-multipath {
        tailf:info "Define how IBGP routes with multiple next hops";
        type empty;
      }

      // router * / bgp /   igp-shortcut
      container igp-shortcut {
        tailf:info "Enables IGP shortcuts for BGP next-hop resolution";
        tailf:cli-embed-no-on-delete;
        tailf:cli-compact-syntax;
        tailf:cli-sequence-commands;

        leaf value {
          tailf:cli-drop-node-name;
          tailf:cli-no-value-on-delete;
          type enumeration {
            enum ldp;
            enum rsvp-te;
            enum mpls;
          }
        }

        leaf disallow-igp {
          tailf:cli-no-name-on-delete;
          type empty;
        }
      }

      // router * / bgp /   import
      leaf-list import {
        tailf:info "Import route policies used to determine which routes";
        tailf:cli-no-value-on-delete;
        tailf:cli-flat-list-syntax;
        type string;
      }

      // router * / bgp /   keepalive
      leaf keepalive {
        tailf:info "Configure BGP keepalive timer";
        tailf:cli-no-value-on-delete;
        type uint16 {
          range "0..21845";
        }
      }

      // router * / bgp / local-as
      container local-as {
        tailf:info "Add/remove a BGP virtual AS number";
        tailf:cli-embed-no-on-delete;
        tailf:cli-compact-syntax;
        tailf:cli-sequence-commands;

        leaf number {
          tailf:cli-no-value-on-delete;
          tailf:cli-no-name-on-delete;
          type uint32;
        }

        leaf private {
          tailf:cli-no-name-on-delete;
          type empty;
        }

        leaf no-prepend-global-as {
          tailf:cli-no-name-on-delete;
          type empty;
        }
      }

      // router * / bgp / local-preference
      leaf local-preference {
        tailf:info "Configure BGP local-preference attribute in routes";
        tailf:cli-no-value-on-delete;
        type uint32;
      }

      // router * / bgp / loop-detect
      leaf loop-detect {
        tailf:info "Configure how the BGP peer session handles loop detect";
        tailf:cli-no-value-on-delete;
        type enumeration {
          enum drop-peer;
          enum discard-route;
          enum ignore-loop;
          enum off;
        }
      }

      // router * / bgp / med-out
      leaf med-out {
        tailf:info "Enable/disable advertising the Multi-Exit Discriminator";
        tailf:cli-no-value-on-delete;
        type union {
          type uint32;
          type enumeration {
            enum igp-cost;
          }
        }
      }

      // router * / bgp / min-as-origination
      leaf min-as-origination {
        tailf:info "Minimum interval at which a given path attribute";
        tailf:cli-no-value-on-delete;
        type uint8 {
          range "2..255";
        }
      }

      // router * / bgp / min-route-advertisement
      leaf min-route-advertisement {
        tailf:info "Minimum interval at which a given prefix is advertised";
        tailf:cli-no-value-on-delete;
        type uint8 {
          range "1..255";
        }
      }

      // router * / bgp / mp-bgp-keep
      leaf mp-bgp-keep {
        tailf:info "Enable/Disable Keep MP-BGP Routes Option";
        type empty;
      }

      // router * / bgp / multihop
      leaf multihop {
        tailf:info "TTL value entered in the IP header of packets sent";
        tailf:cli-no-value-on-delete;
        type uint8 {
          range "1..255";
        }
      }

      // router * / bgp /   multipath
      leaf multipath {
        tailf:info "Configure multipath to share load traffic across";
        tailf:cli-no-value-on-delete;
        type uint8 {
          range "1..32";
        }
      }

      // router * / bgp / mvpn-vrf-import-subtype-new
      leaf mvpn-vrf-import-subtype-new {
          tailf:info "Configure Mvpn VRF Import sub-type under this instance";
          type empty;
        }

        // router * / bgp / next-hop-resolution
        container next-hop-resolution {
        tailf:info "Configure Next-hop Resolution";
        tailf:cli-add-mode;

        // router * / bgp / next-hop-resolution / policy
        leaf policy {
          tailf:info "Configure Next-Hop Resolution policy";
          tailf:cli-no-value-on-delete;
          type string;
        }

        // router * / bgp / next-hop-resolution / use-bgp-routes
        leaf use-bgp-routes {
          tailf:info "Enable/Disable Use BGP routes to resolve BGP nh";
          type empty;
        }
      }

      // router * / bgp / outbound-route-filtering
      container outbound-route-filtering {
        tailf:info "Enable/disable outbound route filtering";
        tailf:cli-add-mode;

        // router * / bgp / outbound-route-filtering / extended-community
        container extended-community {
          tailf:info "Enable/disable outbound route filtering"
            +" using extended communities";
          tailf:cli-add-mode;

          // router * / bgp / outbound-route-filtering /
          // extended-community / accept-orf
          leaf accept-orf {
            tailf:info "Enable/disable acceptance of ORFs";
            type empty;
          }

          // router * / bgp / outbound-route-filtering /
          // extended-community / send-orf
          leaf-list send-orf {
            tailf:info "Add/Remove members to the send ORF list";
            tailf:cli-no-value-on-delete;
            tailf:cli-flat-list-syntax;
            type union {
              type uint32;
              type inet:ipv4-address;
            }
          }
        }
      }

      // router * / bgp / path-mtu-discovery
      leaf path-mtu-discovery {
        tailf:info "Enable/disable Path MTU Discovery";
        type empty;
      }

      // router * / bgp / peer-tracking-policy
      leaf peer-tracking-policy {
        tailf:info "Configure Peer-Tracking policy";
        tailf:cli-no-value-on-delete;
        type string;
      }

      // router * / bgp / preference
      leaf preference {
        tailf:info "Configure the route preference for routes learned";
        tailf:cli-no-value-on-delete;
        type uint8 {
          range "1..255";
        }
      }

      // router * / bgp / purge-timer
      leaf purge-timer {
        tailf:info "Configure the maximum time before stale routes purged";
        tailf:cli-no-value-on-delete;
        type uint8 {
          range "1..60";
        }
      }

      // router * / bgp / rapid-update
      leaf-list rapid-update {
        tailf:info "Enable/Disable BGP rapid update for addr-families";
        tailf:cli-flat-list-syntax;
        tailf:cli-no-value-on-delete;
        type enumeration {
          enum l2-vpn;
          enum mvpn-ipv4;
          enum mdt-safi;
          enum mvpn-ipv6;
        }
      }

      // router * / bgp / rapid-withdrawal
      leaf rapid-withdrawal {
        tailf:info "Disable/Enable the delay on sending BGP"
          + " rapid withdrawals";
        type empty;
      }

      // router * / bgp / remove-private
      leaf remove-private {
        tailf:info "Remove private AS numbers from the AS Path";
        tailf:cli-no-value-on-delete;
        type enumeration {
          enum limited;
          enum skip-peer-as;
        }
      }

      // router * / bgp / route-target-list
      leaf-list route-target-list {
        tailf:info "Add/Remove members to a route-target-list";
        tailf:cli-no-value-on-delete;
        tailf:cli-flat-list-syntax;
        type union {
          type uint32;
          type inet:ipv4-address;
        }
      }

      // router * / bgp / router-id
      leaf router-id {
        tailf:info "Configure the router ID to be used with"
          +" this BGP instance";
        tailf:cli-no-value-on-delete;
        type union {
          type inet:ipv4-address;
          type inet:ipv6-address;
        }
      }

      // router * / bgp / split-horizon
      leaf split-horizon {
        tailf:info "Configure split horizon for the peers"
          +" under this instance";
        type empty;
      }

      // router * / bgp / transport-tunnel
      leaf transport-tunnel {
        tailf:info "Enable mechanism to be used for transport";
        tailf:cli-no-value-on-delete;
        type enumeration {
          enum ldp;
          enum rsvp-te;
          enum mpls;
        }
      }

      // router * / bgp / vpn-apply-export
      leaf vpn-apply-export {
        tailf:info "Enable/disable BGP VPN export policy";
        type empty;
      }

      // router * / bgp / vpn-apply-import
      leaf vpn-apply-import {
        tailf:info "Enable/disable BGP VPN import policy";
        type empty;
      }

      // router * / bgp / shutdown
      leaf shutdown {
        tailf:info "Administratively enable/disable the BGP instance";
        tailf:cli-boolean-no;
        default false;
        type boolean;
      }
    }

    // router * / ecmp
    leaf ecmp {
      tailf:info "Enable/disable ECMP and configure max number "
              +"of routes for path sharing";
      tailf:cli-no-value-on-delete;
      type uint8 {
        range "0..32";
      }
    }

    // router * / fib-priority
    leaf fib-priority {
      tailf:info "Specify the FIB Priority";
      type enumeration {
        enum high;
        enum standard;
      }
    }

    // router * / ldp-shortcut
    leaf ldp-shortcut {
      tailf:info "Allow IGP route resolution using LDP LSPs across network"
                +" interfaces participating in IS-IS and OSPF";
      tailf:cli-no-value-on-delete;
      default ipv4;
      type enumeration {
        enum ipv4;
        enum ipv6;
      }

    }

    // router * / router-id
    leaf router-id {
      tailf:cli-no-value-on-delete;
      type inet:ipv4-address;
    }

    // router * / static-route *
    list static-route {
      tailf:info "Creates/deletes static route entries";
      tailf:cli-compact-syntax;
      tailf:cli-sequence-commands;
      tailf:cli-embed-no-on-delete;
      tailf:cli-delete-when-empty;
      tailf:cli-suppress-mode;
      key route;
      leaf route {
        type union {
          type tailf:ipv4-address-and-prefix-length;
          type tailf:ipv6-address-and-prefix-length;
        }
      }

      choice nh {
        // router * / static-route * next-hop
        leaf next-hop {
          type union {
            type inet:ipv4-address;
            type inet:ipv6-address;
            type string;
          }
        }

        // router * / static-route * indirect
        leaf indirect {
          type inet:ipv4-address;
        }

        // router * / static-route * black-hole
        leaf black-hole {
          type empty;
        }
      }

      // router * / static-route * / preference
      leaf preference {
        tailf:cli-break-sequence-commands;
        type uint8 {
          range "1..255";
        }
      }

      // router * / static-route * / metric
      leaf metric {
        type uint16;
      }

      choice ed {
        // router * / static-route * / enable
        leaf enable {
          type empty;
        }

        // router * / static-route * / disable
        leaf disable {
          type empty;
        }
      }

      // router * / static-route * / ldp
      leaf ldp {
        type empty;
      }

      // router * / static-route * / disallow-igp
      leaf disallow-igp {
        type empty;
      }

      // router * / static-route * / tag
      leaf tag {
        type uint32 {
          range "1..4294967295";
        }
      }

      // router * / static-route * / bfd-enable
      leaf bfd-enable {
        tailf:info "enables BFD sessions on this static route";
        type empty;
      }

      // router * / static-route * / mcast-family
      leaf mcast-family {
        type enumeration {
          enum mcast-ipv4;
          enum mcast-ipv6;
        }
      }

      // router * / static-route * / rsvp-te
      leaf rsvp-te {
        type empty;
      }

      // router * / static-route * / cpe-ip-address
      leaf cpe-ip-address {
        type inet:ipv4-address;
      }

      // router * / static-route * / seconds
      leaf seconds {
        type uint8 {
          range "1..255";
        }
      }

      // router * / static-route * / count
      leaf count {
        type uint8 {
          range "1..255";
        }
      }

      // router * / static-route * / log
      leaf log {
        type empty;
      }

      // router * / static-route * / prefix-list-name
      leaf prefix-list-name {
        type string {
          length "1..32";
        }
      }

      choice an {
        // router * / static-route * / all
        leaf all {
          type empty;
        }

        // router * / static-route * / none
        leaf none {
          type empty;
        }
      }

      // router * / static-route * / ldp-sync
      leaf ldp-sync {
        type empty;
      }

      // router * / static-route * / fc-name
      leaf fc-name {
        type enumeration {
          enum be;
          enum l2;
          enum af;
          enum l1;
          enum h2;
          enum ef;
          enum h1;
          enum nc;
        }
      }

      choice lh {
        // router * / static-route * / low
        leaf low {
          type empty;
        }

        // router * / static-route * / high
        leaf high {
          type empty;
        }
      }
    }

    // router * / isis *
    list isis {
      tailf:info "Create/Configure or delete ISIS instance";
      tailf:cli-embed-no-on-delete;
      key id;

      leaf id {
        type uint32;
      }

      // router * / isis * / all-l1isis
      leaf all-l1isis {
        tailf:info "Specify the MAC address to use for All L1 ISIS routers";
        tailf:cli-no-value-on-delete;
        type string;
      }

      // router * / isis * / all-l2isis
      leaf all-l2isis {
        tailf:info "Specify the MAC address to use for All L2 ISIS routers";
        tailf:cli-no-value-on-delete;
        type string;
      }

      // router * / isis * / area-id
      leaf area-id {
        tailf:info "Configure an area-id used by ISIS (upto 13 bytes)";
        type string;
      }

      // router * / isis * / iid-tlv-enable
      leaf iid-tlv-enable {
        tailf:info "Enable use of IID TLV for this ISIS instance";
        type empty;
      }

      // router * / isis * / ipv4-routing
      leaf ipv4-routing {
        tailf:info "Enable/Disable IPv4 routing";
        type empty;
      }

      // router * / isis * / ipv4-multicast-routing
      leaf ipv4-multicast-routing {
        tailf:info "Enable/Disable IPv4 routing";
        tailf:cli-no-value-on-delete;
        type enumeration {
          enum native;
          enum mt;
        }
      }

      // router * / isis * / ipv6-routing
      leaf ipv6-routing {
        tailf:info "Enable/Disable IPv6 routing";
        tailf:cli-no-value-on-delete;
        type enumeration {
          enum native;
          enum mt;
        }
      }

      // router * / isis * / ipv6-multicast-routing
      leaf ipv6-multicast-routing {
        tailf:info "Enable/Disable IPv6 multicast-routing";
        tailf:cli-no-value-on-delete;
        type enumeration {
          enum native;
          enum mt;
        }
      }

      // router * / isis * / lsp-lifetime
      leaf lsp-lifetime {
        tailf:info "Configure LSP lifetime";
        tailf:cli-no-value-on-delete;
        type uint16 {
          range "350..65535";
        }
      }

      // router * / isis * / lsp-refresh-interval
      leaf lsp-refresh-interval {
        tailf:info "Configure LSP refresh interval";
        type uint32;
      }

      // router * / isis * / lsp-wait
      container lsp-wait {
        tailf:info "Configure ISIS LSP wait times";
        tailf:cli-embed-no-on-delete;
        tailf:cli-compact-syntax;
        tailf:cli-sequence-commands;

        leaf wait {
          tailf:cli-drop-node-name;
          tailf:cli-no-value-on-delete;
          type uint8 {
            range "1..120";
          }
        }

        leaf initial-wait {
          tailf:cli-drop-node-name;
          tailf:cli-no-value-on-delete;
          type uint8 {
            range "0..100";
          }
        }

        leaf second-wait {
          tailf:cli-drop-node-name;
          tailf:cli-no-value-on-delete;
          type uint8 {
            range "1..100";
          }
        }
      }

      // router * / isis * / level
      list level {
        tailf:info "Configure the default global parameters "
              + "both level one and two interfaces";
        key id;
        leaf id {
          type enumeration {
            enum 1;
            enum 2;
          }
        }

        // router * / isis * / level / authentication-key
        container authentication-key {
          tailf:info "Configure the authentication-key to be used";
          tailf:cli-embed-no-on-delete;
          tailf:cli-compact-syntax;
          tailf:cli-sequence-commands;

          leaf key {
            tailf:cli-drop-node-name;
            tailf:cli-no-value-on-delete;
            type string;
          }

          leaf keyword {
            tailf:cli-drop-node-name;
            tailf:cli-no-value-on-delete;
            type enumeration {
              enum hash;
              enum hash2;
            }
          }
        }

        // router * / isis * / level / authentication-type
         leaf authentication-type {
           tailf:info "Configure the authentication type to be used";
           tailf:cli-no-value-on-delete;
           type enumeration {
             enum password;
             enum message-digest;
           }
         }

        // router * / isis * / level / csnp-authentication
         leaf csnp-authentication {
           tailf:info "Enable/disable authentication per CSNP message "
                     + "type at ISIS level.";
           type empty;
         }

        // router * / isis * / level / default-ipv6-unicast-metric
         leaf default-ipv6-unicast-metric {
           tailf:info "Configure default metric for IPv6 unicast";
           tailf:cli-no-value-on-delete;
           type uint32 {
             range "1..16777215";
           }
         }

        // router * / isis * / level / default-metric
         leaf default-metric {
           tailf:info "Configure default metric for IPv4 unicast";
           tailf:cli-no-value-on-delete;
           type uint32 {
             range "1..16777215";
           }
         }

        // router * / isis * / level / external-preference
         leaf external-preference {
           tailf:info "Configure external-preference";
           tailf:cli-no-value-on-delete;
           type uint8 {
             range "1..255";
           }
         }

        // router * / isis * / level / hello-authentication
         leaf hello-authentication {
           tailf:info "Enable/disable authentication per HELLO "
                     + "message type at ISIS level.";
          type empty;
         }

        // router * / isis * / level /  loopfree-alternate-exclude
         leaf loopfree-alternate-exclude {
           tailf:info "Enable/disable LFA at ISIS level.";
          type empty;
         }

        // router * / isis * / level / preference
         leaf preference {
           tailf:info "Configure preference";
           tailf:cli-no-value-on-delete;
           type uint8 {
             range "1..255";
           }
         }

        // router * / isis * / level / psnp-authentication
         leaf psnp-authentication {
           tailf:info "Enable/disable authentication per "
                 + "PSNP message type at ISIS level.";
           type empty;
         }

        // router * / isis * / level / wide-metrics-only
         leaf wide-metrics-only {
           tailf:info "Enable/disable wide-metrics advertisements in the LSPs";
          type empty;
        }
      }

      // router * / isis * / link-group *
      list link-group {
        tailf:cli-embed-no-on-delete;
        key name;
        leaf name {
          type string;
        }

        // router * / isis * / link-group * / level *
        list level {
          tailf:cli-embed-no-on-delete;
          key id;
          leaf id {
            type enumeration {
              enum 1;
              enum 2;
            }
          }

          // router * / isis * / link-group * / level * /
          // ipv6-unicast-metric-offset
          leaf ipv6-unicast-metric-offset {
            tailf:cli-no-value-on-delete;
            type uint8;
          }

          // router * / isis * / link-group * / level * / member
          list member {
            tailf:cli-suppress-mode;
            key name;
            leaf name {
              type string;
            }
          }

          // router * / isis * / link-group * / level * / revert-members
          leaf revert-members {
            tailf:cli-no-value-on-delete;
            type uint32;
          }

          // router * / isis * / link-group * / level * / oper-members
          leaf oper-members {
            tailf:cli-no-value-on-delete;
            type uint32;
          }
        }
      }

      // router * / isis * / multi-topology
      container multi-topology {
        tailf:info "Enable/disable IS-IS multi-topology support";
        tailf:cli-add-mode;

        // router * / isis * / multi-topology / ipv6-unicast
        leaf ipv6-unicast {
          tailf:cli-embed-no-on-delete;
          type empty;
        }
      }

      // router * / isis * / interface
      list interface {
        tailf:info "Configure ISIS interface";
        tailf:cli-embed-no-on-delete;
        tailf:cli-recursive-delete;
        key name;
        leaf name {
          tailf:non-strict-leafref {
            path "/alu:router/interface/interface-name";
          }
          type string;
        }

        // router * / isis * / interface * / bfd-enable
        leaf bfd-enable {
          tailf:info "Enable-BFD";
          type enumeration {
            enum ipv4;
            enum ipv6;
          }
        }

        // router * / isis * / interface * / csnp-interval
        leaf csnp-interval {
          tailf:info "Configure the frequency that CSN packets"
            +" are sent from this interface";
          type uint16 {
            range "1..65535";
          }
        }


        // router * / isis * / interface * / hello-authentication
        leaf hello-authentication {
          tailf:info "Enable/disable hello-authentication on the interface";
          type empty;
        }

        // router * / isis * / interface * / hello-authentication-key
        container hello-authentication-key {
          tailf:info "Configure the authentication-key";
          tailf:cli-embed-no-on-delete;
          tailf:cli-sequence-commands;
          tailf:cli-compact-syntax;

          leaf key {
            tailf:cli-drop-node-name;
            tailf:cli-no-value-on-delete;
            type string;
          }

          leaf type {
            tailf:cli-drop-node-name;
            tailf:cli-no-value-on-delete;
            type enumeration {
              enum hash;
              enum hash2;
            }
          }
        }

        // router * / isis * / interface * / hello-authentication-type
        leaf hello-authentication-type {
          tailf:info "Configure hello-authentication-type to be enabled";
          tailf:cli-no-value-on-delete;
          type enumeration {
            enum password;
            enum message-digest;
          }
        }

        // router * / isis * / interface * / interface-type
        leaf interface-type {
          tailf:info "Configure the interface type";
          tailf:cli-no-value-on-delete;
          type enumeration {
            enum broadcast;
            enum point-to-point;
          }
        }

        // router * / isis * / interface * / ipv4-multicast-enable
        leaf ipv4-multicast-enable {
          tailf:info "Disable IS-IS IPv4 multicast routing for the interface";
          type empty;
        }

        // router * / isis * / interface * / ipv6-multicast-enable
        leaf ipv6-multicast-enable {
          tailf:info "Disable IS-IS IPv6 multicast routing for the interface";
          type empty;
        }

        // router * / isis * / interface * / ipv6-unicast-enable
        leaf ipv6-unicast-enable {
          tailf:info "Disable IS-IS IPv6 unicast routing for the interface";
          type empty;
        }

        // router * / isis * / interface * / level *
        list level {
          tailf:info "Configure the default parameters for level"
            +" one and two interfaces";
          tailf:cli-embed-no-on-delete;
          key id;

          leaf id {
            type uint8 {
              range "1..2";
            }
          }


          // router * / isis * / interface * / level * /
          // hello-authentication-key
          container hello-authentication-key {
            tailf:info "Configure the authentication-key";
            tailf:cli-embed-no-on-delete;
            tailf:cli-sequence-commands;
            tailf:cli-compact-syntax;

            leaf key {
              tailf:cli-drop-node-name;
              tailf:cli-no-value-on-delete;
              type string;
            }

            leaf type {
              tailf:cli-drop-node-name;
              tailf:cli-no-value-on-delete;
              type enumeration {
                enum hash;
                enum hash2;
              }
            }
          }

          // router * / isis * / interface * / level * /
          // hello-authentication-type
          leaf hello-authentication-type {
            tailf:info "Configure hello-authentication-type to be enabled";
            tailf:cli-no-value-on-delete;
            type enumeration {
              enum password;
              enum message-digest;
            }
          }

          // router * / isis * / interface * / level * / hello-interval
          leaf hello-interval {
            tailf:info "Configure hello-interval for this interface";
            tailf:cli-no-value-on-delete;
            type uint16 {
              range "1..20000";
            }
          }

          // router * / isis * / interface * / level * / hello-multiplier
          leaf hello-multiplier {
            tailf:info "Configure hello-multiplier for this level";
            tailf:cli-no-value-on-delete;
            type uint8 {
              range "2..100";
            }
          }

          // router * / isis * / interface * / level * / ipv4-multicast-metric
          leaf ipv4-multicast-metric {
            tailf:info "Configure IS-IS interface metric for IPv4 multicast";
            tailf:cli-no-value-on-delete;
            type uint32 {
              range "1..16777215";
            }
          }

          // router * / isis * / interface * / level * / ipv6-multicast-metric
          leaf ipv6-multicast-metric {
            tailf:info "Configure IS-IS interface metric for IPv6 multicast";
            tailf:cli-no-value-on-delete;
            type uint32 {
              range "1..16777215";
            }
          }

          // router * / isis * / interface * / level * / ipv6-unicast-metric
          leaf ipv6-unicast-metric {
            tailf:info "Configure IS-IS interface metric for IPv6 unicast";
            tailf:cli-no-value-on-delete;
            type uint32 {
              range "1..16777215";
            }
          }

          // router * / isis * / interface * / level * / metric
          leaf metric {
            tailf:info "Configure IS-IS interface metric for IPv4 unicast";
            tailf:cli-no-value-on-delete;
            type uint32 {
              range "1..16777215";
            }
          }

          // router * / isis * / interface * / level * / passive
          leaf passive {
            tailf:info "Configure passive";
            type empty;
          }

          // router * / isis * / interface * / level * / priority
          leaf priority {
            tailf:info "Configure the priority that serves"
              + " to determine router";
            tailf:cli-no-value-on-delete;
            type uint8 {
              range "0..127";
            }
          }

          // router * / isis * / interface * / level * / sd-offset
          leaf sd-offset {
            tailf:info "Configure the signal degrade offset";
            tailf:cli-no-value-on-delete;
            type uint32 {
              range "1..16777215";
            }
          }

          // router * / isis * / interface * / level * / sd-offset
          leaf sf-offset {
            tailf:info "Configure the signal fail offset";
            tailf:cli-no-value-on-delete;
            type uint32 {
              range "1..16777215";
            }
          }
        }

        // router * / isis * / level-capability
        leaf level-capability {
          tailf:info "Specifies ISIS levels for this interface";
          tailf:cli-no-value-on-delete;
          type enumeration {
            enum level-1;
            enum level-2;
            enum level-1/2;
          }
        }

        // router * / isis * / interface * / loopfree-alternate-exclude
        leaf loopfree-alternate-exclude {
          tailf:info "Enable/disable LFA for ISIS on this interface";
          type empty;
        }

        // router * / isis * / interface * / loopfree
        leaf lsp-pacing-interval {
          tailf:info "Configure the interval between LSP packets are sent";
          tailf:cli-no-value-on-delete;
          type uint16;
        }

        // router * / isis * / interface * / mesh-group
        leaf mesh-group {
          tailf:info "Configure mesh groups";
          tailf:cli-no-value-on-delete;
          type union {
            type uint32 {
              range "1..2000000000";
            }
            type enumeration {
              enum blocked;
            }
          }
        }

        // router * / isis * / interface * / passive
        leaf passive {
          tailf:info "Configure passive interface";
          type empty;
        }

        // router * / isis * / interface * / retransmit-interval
        leaf retransmit-interval {
          tailf:info "Configure the minimum interval between LSP retrans";
          tailf:cli-no-value-on-delete;
          type uint16 {
            range "1..65535";
          }
        }

        // router * / isis * / interface * / tag
        leaf tag {
          tailf:info "Configure a route tag to the IP addr of an interface";
          tailf:cli-no-value-on-delete;
          type uint32;
        }

        // router * / isis * / interface * / shutdown
        leaf shutdown {
          tailf:info "Administratively Enable/disable the interface";
          tailf:cli-boolean-no;
          default false;
          type boolean;
        }
      }

      // router * / isis * / level-capability
      leaf level-capability {
        tailf:info "Specifies ISIS levels on the system";
        tailf:cli-no-value-on-delete;
        type enumeration {
          enum level-1;
          enum level-2;
          enum level-1/2;
        }
      }

      // router * / isis * / lsp-wait
      container spf-wait {
        tailf:info "Configure ISIS SPF wait times";
        tailf:cli-embed-no-on-delete;
        tailf:cli-compact-syntax;
        tailf:cli-sequence-commands;

        leaf wait {
          tailf:cli-drop-node-name;
          tailf:cli-no-value-on-delete;
          type uint8 {
            range "1..120";
          }
        }

        leaf initial-wait {
          tailf:cli-drop-node-name;
          tailf:cli-no-value-on-delete;
          type uint32 {
            range "10..100000";
          }
        }

        leaf second-wait {
          tailf:cli-drop-node-name;
          tailf:cli-no-value-on-delete;
          type uint32 {
            range "1..100000";
          }
        }
      }

      // router * / isis * / shutdown
      leaf shutdown {
        tailf:info "Administratively enable or disable the operation of ISIS";
        tailf:cli-boolean-no;
        default false;
        type boolean;
      }
    }

    // router * / ospf *
    list ospf {
      tailf:info "Create/Configure or delete OSPF instance";
      key ospf-instance;
      leaf ospf-instance {
        type uint8 {
          range "0..31";
        }
      }

      // router * / ospf * router-id
      leaf router-id {
        tailf:info "Configure router-id for OSPF";
        tailf:cli-drop-node-name;
        tailf:cli-no-value-on-delete;
        tailf:cli-hide-in-submode;
        default "0.0.0.0";
        type inet:ipv4-address;
      }

      // router * / ospf * / advertise-tunnel-link
      leaf advertise-tunnel-link {
        tailf:info "Enable/disable advertisement of tunnel link";
        type empty;
      }

      // router * / ospf * / area *
      list area {
        tailf:info "Configure an OSPF area";
        key area-id;

        leaf area-id {
          type inet:ipv4-address;
        }

        // router * / ospf * / area * / nssa
        container nssa {
          tailf:info "Configure an OSPF Not So Stubby Area (NSSA)";
          tailf:cli-add-mode;
          tailf:cli-embed-no-on-delete;

          leaf area-range {
            tailf:info "address ranges for route sum/suppression";
            tailf:cli-embed-no-on-delete;
            type empty;
          }
        }

        // router * / ospf * / area * / interface
        list interface {
          tailf:info "Configure OSPF on an IP interface";
          tailf:cli-embed-no-on-delete;
          tailf:cli-diff-dependency "/alu:router/interface/interface-name" {
            tailf:cli-trigger-on-all;
          }
          key name;
          leaf name {
            tailf:non-strict-leafref {
              path "/alu:router/interface/interface-name";
            }
            type string;
          }

          // router * / ospf * / area * / interface / passive
          leaf passive {
            tailf:info "Add/remove the passive property to/from the interface";
            tailf:cli-boolean-no;
            default true;
            type boolean;
          }

          // router * / ospf * / area * / nssa / interface /
          container message-digest-key {
            tailf:info "Configure a message digest key when MD5"
            + " authentication";
            tailf:cli-compact-syntax;
            tailf:cli-embed-no-on-delete;
            tailf:cli-break-sequence-commands;
            leaf key {
              tailf:cli-drop-node-name;
              type uint32;
            }

            // router * / ospf * / area * / nssa / interface / md5
            leaf md5 {
              type empty;
            }

            // router * / ospf * / area * / nssa / interface / hash-value
            leaf hash-value {
              tailf:cli-drop-node-name;
              type string;
            }

            // router * / ospf * / area * / nssa / interface / hash2
            leaf hash2 {
              type empty;
            }
          }

          // router * / ospf * / area * / interface / interface-type
          leaf interface-type {
            tailf:info "Configure the interface type to be either "
                      +"broadcast or point-to-point";
            type enumeration {
              enum "broadcast";
              enum "point-to-point";
            }
          }

          // router * / ospf * / area * / interface / metric
          leaf metric {
            tailf:info "Configure an explicit route cost metric "
                      +"for the interface";
            type uint32;
          }

          // router * / ospf * / area * / interface / authentication-type
          leaf authentication-type {
            tailf:info "Configure the authentication type to be used";
            tailf:cli-no-value-on-delete;
            type enumeration {
              enum password;
              enum message-digest;
            }
          }

          // router * / ospf * / area * / interface / bfd-enable
          leaf bfd-enable {
            tailf:info "Enable BFD";
            type empty;
          }

          // router * / ospf * / area * / interface / shutdown
          leaf shutdown {
            tailf:cli-boolean-no;
            default false;
            type boolean;
          }
        }
      }

      // router * / ospf * / asbr
      leaf asbr {
        tailf:info "Configure the router as an ASBR "
                 + "(Autonomous System Boundary Router)";
        type empty;
      }

      // router * / ospf * / compatible-rfc1583
      leaf compatible-rfc1583 {
        tailf:info "Enable/disable OSPF summary and external route"
                  +" calculations in compliance with RFC1583 and earlier";
        type empty;
      }

      // router * / ospf * / disable-ldp-sync
      leaf disable-ldp-sync {
        tailf:info "Disable/Enable synchronization of IGP and LDP";
        type empty;
      }

      // router * / ospf * / export
      leaf-list export {
        tailf:info "Configure export route policies to determine which"
                   + " routes are exported from the route table";
        tailf:cli-no-value-on-delete;
        tailf:cli-flat-list-syntax;
        type string;
      }

      // router * / ospf * / export-limit
      container export-limit {
        tailf:info "Maximum number of routes (prefixes) that can be exported"
                  +" into OSPF from the route table.";
        tailf:cli-compact-syntax;
        tailf:cli-sequence-commands;
        tailf:cli-embed-no-on-delete;

        leaf limit {
          tailf:cli-drop-node-name;
          tailf:cli-no-value-on-delete;
          type uint32;
        }

        leaf log {
          tailf:cli-no-name-on-delete;
          tailf:cli-no-value-on-delete;
          type uint8 {
            range "0..100";
          }
        }
      }

      // router * / ospf * / external-db-overflow
      container external-db-overflow {
        tailf:info "Limit on number of AS-external-LSAs in LSDB and wait"
                 +" time before processing these if limit is exceeded";
        tailf:cli-compact-syntax;
        tailf:cli-sequence-commands;
        tailf:cli-embed-no-on-delete;

        leaf limit {
          tailf:cli-drop-node-name;
          tailf:cli-no-value-on-delete;
          type int32 {
            range "-1..2147483647";
          }
        }

        leaf seconds {
          tailf:cli-drop-node-name;
          tailf:cli-no-value-on-delete;
          type uint32 {
            range "0..2147483647";
          }
        }
      }

      // router * / ospf * / external-preference
      leaf external-preference {
        tailf:info "Preference for OSPF external routes";
        tailf:cli-no-value-on-delete;
        type uint8 {
          range "1..255";
        }
      }

      // router * / ospf * / graceful-restart
      container graceful-restart {
        tailf:info "Enable/disable graceful-restart for OSPF";
        tailf:cli-add-mode;
        tailf:cli-embed-no-on-delete;

        // router * / ospf * / graceful-restart / helper-disable
        leaf helper-disable {
          tailf:info "Enable/disable graceful restart helper mode for OSPF";
          tailf:cli-embed-no-on-delete;
          type empty;
        }
      }

      // router * / ospf * / ldp-over-rsvp
      leaf ldp-over-rsvp {
        tailf:info "Allow ldp over rsvp processing in this OSPF instance";
        type empty;
      }

      // router * / ospf * / multicast-import
      leaf multicast-import {
        tailf:info "Enable/disable submission of routes into the multicast"
                  +" Route Table Manager by OSPF";
        type empty;
      }

      // router * / ospf * / overload
      leaf overload {
        tailf:info "Configure the local router so that it appears to be"
                 + " overloaded";
        tailf:cli-no-value-on-delete;
        type uint16 {
          range "1..1800";
        }
      }

      // router * / ospf * / overload-include-stub
      leaf overload-include-stub {
        tailf:info "Enable/disable OSPF maximum metric usage for stub"
                 + " advertisement in case of overload";
        type empty;
      }

      // router * / ospf * / overload-on-boot
      container overload-on-boot {
        tailf:info "Configure the local router so that it appears "
                  +"to be overloaded at boot up";
        tailf:cli-embed-no-on-delete;
        tailf:cli-compact-syntax;
        presence true;

        leaf timeout {
          tailf:cli-no-name-on-delete;
          tailf:cli-no-value-on-delete;
          type uint16 {
            range "1..1800";
          }
        }
      }

      // router * / ospf * / preference
      leaf preference {
        tailf:info "Preference for OSPF internal routes";
        tailf:cli-no-value-on-delete;
        type uint8 {
          range "1..255";
        }
      }

      // router * / ospf * / reference-bandwidth
      leaf reference-bandwidth {
        tailf:info "Reference bandwidth that provides a reference for the"
                  +" default costing of interfaces";
        tailf:cli-no-value-on-delete;
        type uint32 {
          range "1..100000000";
        }
      }

      // router * / ospf * / rsvp-shortcut
      leaf rsvp-shortcut {
        tailf:info "Enable/disable RSVP shortcut";
        type empty;
      }

      // router * / ospf * / timers
      container timers {
        tailf:info "Configure OSPF timers";
        tailf:cli-embed-no-on-delete;
        tailf:cli-add-mode;

        // router * / ospf * / timers / lsa-arrival
        leaf lsa-arrival {
          tailf:info "Configure the LSA arrival time";
          type uint16;
        }

        // router * / ospf * / timers / lsa-generate
        leaf lsa-generate {
          tailf:info "Configure the minimum delay that must pass between";
          type uint16;
        }

        // router * / ospf * / timers / spf-wait
        leaf spf-wait {
          tailf:info "Configure the minimum delay that must pass between";
          type uint16;
        }
      }

      // router * / ospf * / traffic-engineering
      leaf traffic-engineering {
        tailf:info "Enable/disable traffic engineering route calculations";
        type empty;
      }

      // router * / ospf * / unicast-import-disable
      leaf unicast-import-disable {
        tailf:info "Enable/disable submission of routes into the unicast"
                  +" Route Table Manager by OSPF";
        type empty;
      }

      // router * / ospf * / shutdown
      leaf shutdown {
        tailf:info "Administratively enable/disable the OSPF instance";
        tailf:cli-boolean-no;
        default false;
        type boolean;
      }
    }

    // router * / ospf3
    container ospf3 {
      tailf:info "Create/Configure or delete OSPF instance";
      tailf:cli-add-mode;
      presence present;
      // router * / ospf3 / area *
      list area {
        key area-id;
        leaf area-id {
          tailf:info "Configure an OSPF3 area";
          type union {
            type inet:ipv4-address;
            type uint32;
          }
        }
        // router * / ospf3 / area * / interface *
        list interface {
          tailf:info "Configure OSPF3 on an IP interface";
          key interface-name;
          leaf interface-name {
            tailf:non-strict-leafref {
              path "/alu:router/interface/interface-name";
            }
            type string;
          }
          // router * / ospf3 / area * / interface * / interface-type
          leaf interface-type {
            tailf:info "Configure the interface type to be either "+
              "broadcast or point-to-point";
            tailf:cli-no-value-on-delete;
            type enumeration {
              enum broadcast;
              enum point-to-point;
            }
          }
          // router * / ospf3 / area * / interface * / passive
          leaf passive {
            tailf:info "Add/remove the passive property to/from the interface";
            type empty;
          }
          // router * / ospf3 / area * / interface * / shutdown
          leaf shutdown {
            tailf:info "Administratively enable/disable OSPF3 on the interface";
            tailf:cli-boolean-no;
            default true;
            type boolean;
          }
        }
      }
      leaf shutdown {
        tailf:info "Administratively enable/disable the operation of OSPF3";
        tailf:cli-boolean-no;
        default true;
        type boolean;
      }
    }

    // router * / msdp
    container msdp {
      tailf:info "Create/Configure or delete MSDP instance";
      tailf:cli-add-mode;
      container local-address {
        tailf:info "Create/Configure or delete MSDP instance";
        tailf:cli-add-mode;
        leaf group {
          type empty;
        }
      }
    }
    // router * / l2tp
    container l2tp {
      tailf:info "Configure L2TP";
      tailf:cli-add-mode;
      tailf:cli-embed-no-on-delete;

      leaf shutdown {
        tailf:info "Administratively enable/disable the operation of L2TP";
        tailf:cli-boolean-no;
        default false;
        type boolean;
      }
    }


    // router * / ldp /
    container ldp {
      tailf:info "Create/Configure or delete LDP instance";
      tailf:cli-add-mode;
      tailf:cli-embed-no-on-delete;
      presence present;

      // router * / ldp / aggregate-prefix-match
      container aggregate-prefix-match {
        tailf:info "Enable/Disable aggregate prefix match procedures";
        tailf:cli-add-mode;
        tailf:cli-embed-no-on-delete;

        // router * / ldp / shutdown
        leaf shutdown {
          tailf:info "Administratively enable/disable LDP instance";
          tailf:cli-boolean-no;
          default false;
          type boolean;
        }
      }

      // router * / ldp / interface-parameters
      container interface-parameters {
        tailf:info "Context to configure LDP interfaces and parameters";
        tailf:cli-recursive-delete;
        tailf:cli-add-mode;
        // router * / ldp / interface-parameters / interface  *
        list interface {
          tailf:info "Configure LDP on an IP interface";
          tailf:cli-embed-no-on-delete;
          key name;
          leaf name {
            tailf:non-strict-leafref {
              path "/alu:router/interface/interface-name";
            }
            type string;
          }
          // router * / ldp / interface-parameters / interface * / shutdown
          leaf shutdown {
            tailf:cli-boolean-no;
            default true;
            type boolean;
          }
        }

        // router * / ldp / interface-parameters
        container hello {
          tailf:info "Configure the hello timeout and factor";
          tailf:cli-embed-no-on-delete;
          tailf:cli-compact-syntax;
          tailf:cli-sequence-commands;

          leaf timeout {
            tailf:cli-drop-node-name;
            type uint16 {
              range "3..65535";
            }
          }

          leaf factor {
            tailf:cli-drop-node-name;
            type uint8 {
              range "1..255";
            }
          }
        }
      }

      // router * / ldp / prefer-tunnel
      leaf prefer-tunnel-in-tunnel {
        tailf:info "Configure preference of tunnel-in-tunnel over a simple"
                  +" LDP tunnel";
        type empty;
      }

      // router * / ldp / targeted-session
      container targeted-session {
        tailf:info "Context to configure LDP targeted peers and parameters";
        tailf:cli-add-mode;

        // router * / ldp / targeted-session / hello
        leaf hello {
          tailf:info "Configure the hello timeout and factor for targeted LDP";
          tailf:cli-embed-no-on-delete;
          type empty;
        }

        // router * / ldp / targeted-session / peer *
        list peer {
          tailf:info "Configure a targeted peer for LDP";
          tailf:cli-embed-no-on-delete;
          key peer-address;

          leaf peer-address {
            type inet:ipv4-address;
          }

          // router * / ldp / targeted-session / peer * / bfd-enable
          leaf bfd-enable {
            tailf:info "Enable/Disable BFD tracking of LDP"
              + " Session for the peer";
            tailf:cli-embed-no-on-delete;
            type empty;
          }

          // router * / ldp / targeted-session / peer * / hello
          container hello {
            tailf:info "Configure the hello timeout and factor for the peer";
            tailf:cli-embed-no-on-delete;
            tailf:cli-compact-syntax;
            tailf:cli-sequence-commands;

            leaf timeout {
              tailf:cli-drop-node-name;
              type uint16 {
                range "3..65535";
              }
            }

            leaf factor {
              tailf:cli-drop-node-name;
              type uint8 {
                range "1..255";
              }
            }
          }

          // router * / ldp / targeted-session / peer * / keepalive
          container keepalive {
            tailf:info "Configure the keepalive timeout and factor"
              +" for the peer";
            tailf:cli-embed-no-on-delete;
            tailf:cli-compact-syntax;
            tailf:cli-sequence-commands;

            leaf timeout {
              tailf:cli-drop-node-name;
              type uint16 {
                range "3..65535";
              }
            }

            leaf factor {
              tailf:cli-drop-node-name;
              type uint8 {
                range "1..255";
              }
            }
          }

          // router * / ldp / targeted-session / peer * / local-lsr-id
          leaf local-lsr-id {
            tailf:info "Configure local lsr-id";
            tailf:cli-embed-no-on-delete;
            type string {
              length "1..32";
            }
          }

          // router * / ldp / targeted-session / peer * / shutdown
          leaf shutdown {
            tailf:info "Administratively enable/disable the peer";
            tailf:cli-boolean-no;
            default true;
            type boolean;
          }
        }
      }

      // router * / ldp / label-withdrawal-delay
      leaf label-withdrawal-delay {
        tailf:info "configure ldp label-withdrawal-delay";
        type uint32;
      }

      // router * / ldp / shutdown
      leaf shutdown {
        tailf:cli-boolean-no;
        default false;
        type boolean;
      }
    }


    // router * / dhcp
    container dhcp {
      tailf:cli-add-mode;

      // router * / dhcp / local-dhcp-server *
      list local-dhcp-server {
        key "id";
        leaf id {
          type string;
        }

        // router * / dhcp / local-dhcp-server * / create
        leaf create {
          tailf:cli-hide-in-submode;
          tailf:cli-no-name-on-delete;
          mandatory true;
          type empty;
        }
      }
    }

    // router * / interface *
    list interface {
      tailf:cli-recursive-delete;
      tailf:cli-embed-no-on-delete;
      tailf:cli-diff-dependency "/alu:lag";
      tailf:cli-diff-dependency "/alu:port";
      key interface-name;
      leaf interface-name {
        type string;
      }

      // router * / interface * / address
      leaf address {
        tailf:cli-no-value-on-delete;
        type tailf:ipv4-address-and-prefix-length;
      }

      // router * / interface * / description
      leaf description {
        tailf:cli-no-value-on-delete;
        type string;
      }

      // router * / interface * / ldp-sync-time
      leaf ldp-sync-time {
        type uint32;
      }

      // router * / interface * / cpu-protection
      leaf cpu-protection {
        type uint32;
      }

      // router * / interface * / loopback
      leaf loopback {
        type empty;
      }

      // router * / interface * / unnumbered-mpls-tp
      leaf unnumbered-mpls-tp {
        tailf:cli-hide-in-submode;
        type empty;
      }

      // router * / interface * / port
      leaf port {
        tailf:cli-no-value-on-delete;
        tailf:cli-diff-dependency "/alu:port/port-id" {
          tailf:cli-trigger-on-all;
        }
        tailf:non-strict-leafref {
          path "/alu:port/port-id";
        }
        type string;
      }

      // router * / interface * / icmp
      container icmp {
        tailf:cli-add-mode;

        // router * / interface * / icmp / redirects
        container redirects {
          tailf:cli-compact-syntax;
          tailf:cli-sequence-commands {
            tailf:cli-reset-siblings;
          }

          // router * / interface * / icmp / redirects a
          leaf a {
            tailf:cli-drop-node-name;
            type uint32;
          }

          // router * / interface * / icmp / redirects b
          leaf b {
            tailf:cli-drop-node-name;
            type uint32;
          }
        }

        // router * / interface * / icmp / redirects unreachables
        container unreachables {
          tailf:cli-compact-syntax;
          tailf:cli-sequence-commands {
            tailf:cli-reset-siblings;
          }

          // router * / interface * / icmp / redirects unreachables a
          leaf a {
            tailf:cli-drop-node-name;
            type uint32;
          }

          // router * / interface * / icmp / redirects unreachables b
          leaf b {
            tailf:cli-drop-node-name;
            type uint32;
          }
        }

        // router * / interface * / icmp / redirects ttl-expired
        container ttl-expired {
          tailf:cli-compact-syntax;
          tailf:cli-sequence-commands {
            tailf:cli-reset-siblings;
          }

          // router * / interface * / icmp / redirects ttl-expired a
          leaf a {
            tailf:cli-drop-node-name;
            type uint32;
          }

          // router * / interface * / icmp / redirects ttl-expired b
          leaf b {
            tailf:cli-drop-node-name;
            type uint32;
          }
        }
      }

      // router * / interface * / qos
      leaf qos {
        tailf:cli-no-value-on-delete;
        tailf:cli-diff-dependency "/alu:qos/network/id" {
          tailf:cli-trigger-on-all;
        }
        tailf:non-strict-leafref {
          path "/alu:qos/network/id";
        }
        type uint16;
      }

      // router * / interface * / ipv6
      container ipv6 {
        tailf:cli-add-mode;

        // router * / interface * / ipv6 / address *
        list address {
          tailf:cli-embed-no-on-delete;
          tailf:cli-suppress-mode;
          key "addr";
          leaf addr {
            type tailf:ipv6-address-and-prefix-length;
          }

          // router * / interface * / ipv6 / address * / eui-64
          leaf eui-64 {
            tailf:cli-hide-in-submode;
            type empty;
          }

          // router * / interface * / ipv6 / address * / preferred
          leaf preferred {
            tailf:cli-hide-in-submode;
            type empty;
          }
        }


        // router * / interface * / ipv6 / bfd
        container bfd {
          tailf:cli-embed-no-on-delete;
          tailf:cli-compact-syntax;
          tailf:cli-sequence-commands;

          leaf id {
            tailf:cli-drop-node-name;
            tailf:cli-no-value-on-delete;
            type uint32;
          }

          leaf receive {
            tailf:cli-no-name-on-delete;
            tailf:cli-no-value-on-delete;
            type uint32;
          }

          leaf multiplier {
            tailf:cli-no-name-on-delete;
            tailf:cli-no-value-on-delete;
            type uint32;
          }

          leaf type {
            tailf:cli-no-name-on-delete;
            tailf:cli-no-value-on-delete;
            type enumeration {
              enum cpm-np;
            }
          }
        }
      }

      // router * / interface * / bfd
      container bfd {
        tailf:info "Configure BFD parameters";
        tailf:cli-embed-no-on-delete;
        tailf:cli-compact-syntax;
        tailf:cli-sequence-commands;

        leaf id {
          tailf:cli-drop-node-name;
          tailf:cli-no-value-on-delete;
          type uint32;
        }

        leaf receive {
          tailf:cli-no-name-on-delete;
          tailf:cli-no-value-on-delete;
          type uint32;
        }

        leaf multiplier {
          tailf:cli-no-name-on-delete;
          tailf:cli-no-value-on-delete;
          type uint32;
        }

        leaf type {
          tailf:cli-no-name-on-delete;
          tailf:cli-no-value-on-delete;
          type enumeration {
            enum cpm-np;
          }
        }
      }

      // router * / interface * / autonomous-system
      leaf autonomous-system {
        tailf:cli-no-value-on-delete;
        type uint16;
      }

      // router * / interface * / shutdown
      leaf shutdown {
         tailf:cli-boolean-no;
        default false;
        type boolean;
      }
    }

    // router * / mpls
    container mpls {
      tailf:info "Create/Configure or delete MPLS instance";
      tailf:cli-embed-no-on-delete;
      tailf:cli-recursive-delete;
      tailf:cli-add-mode;
      tailf:callpoint mpls-hook { tailf:set-hook node; }
      presence true;
      // router * / mpls / resignal-timer
      leaf resignal-timer {
        tailf:info "Configure the resignal timer for the MPLS instance";
        tailf:cli-no-value-on-delete;
        type uint16{
          range "30..10080";
        }
      }
      // router * / mpls / srlg-frr
      container srlg-frr {
        tailf:info "Enable/disable SRLG for FRR path computation";
        tailf:cli-compact-syntax;
        presence present;
        leaf strict {
          tailf:cli-no-name-on-delete;
          type empty;
        }
      }

      // router * / mpls / interface *
      list interface {
        tailf:info "Configure MPLS on an IP interface";
        tailf:cli-embed-no-on-delete;
        key name;
        leaf name {
          tailf:non-strict-leafref {
            path "/alu:router/interface/interface-name";
          }
          type string;
        }

        // router * / mpls / interface * / shutdown
        leaf shutdown {
          tailf:info "Administratively enable/disable MPLS on the interface";
          tailf:cli-boolean-no;
          default false;
          type boolean;
        }
      }

      // router * / mpls / path *
      list path {
        tailf:info "Configure the path to be used for a LSP";
        tailf:cli-embed-no-on-delete;
        key name;
        leaf name {
          type string;
        }

        // router * / mpls / path * / shutdown
        leaf shutdown {
          tailf:info "Administratively enable/disable the LSP path";
          tailf:cli-embed-no-on-delete;
          tailf:cli-boolean-no;
          default true;
          type boolean;
        }
      }

      // router * / mpls / lsp-template
      list lsp-template {
        tailf:info "Creates an LSP Template that will be referenced";
        tailf:cli-embed-no-on-delete;
        key template;

        leaf template {
          tailf:cli-hide-in-submode;
          type string;
        }

        // router * / mpls / lsp-template * p2mp
        leaf p2mp {
          tailf:cli-hide-in-submode;
          type empty;
        }

        // router * / mpls / lsp-template * / default-path
        leaf default-path {
          tailf:info "Specify default path to be used for signaling LSP";
          tailf:cli-embed-no-on-delete;
          type string;
        }

        // router * / mpls / lsp-template * fast-reroute /
        // router * / mpls / lsp * / fast-reroute /
        container fast-reroute {
          tailf:info "Configure fast reroute for LSP";
          tailf:cli-add-mode;
          tailf:cli-embed-no-on-delete;

          // router * / mpls / lsp-template * / fast-reroute / frr-method
          leaf frr-method {
            tailf:info "<frr-method>;;one-to-one|facility";
            tailf:cli-hide-in-submode;
            tailf:cli-drop-node-name;
            type enumeration {
              enum facility;
              enum one-to-one;
            }
          }

          // router * / mpls / lsp-template * / fast-reroute / hop-limit
          leaf hop-limit {
            tailf:info "Configure hop limit  for fast reroute";
            tailf:cli-embed-no-on-delete;
            type empty;
          }
        }

        // router * / mpls / lsp-template * / cspf
        leaf cspf {
          tailf:info "Enable/disable CSPF support for for LSP instances created"
                    +" using this LSP template";
          type empty;
        }

        // router * / mpls / lsp-template * / shutdown
        leaf shutdown {
          tailf:info "Administratively enable/disable the LSP Template";
          tailf:cli-boolean-no;
          default true;
          type boolean;
        }
      }

      // router * / mpls / lsp *
      list lsp {
        tailf:info "Creates an LSP that will be signaled dynamically";
        tailf:cli-embed-no-on-delete;
        tailf:cli-compact-syntax;
        key name;
        leaf name {
          type string;
        }
        leaf bypass-only {
          tailf:cli-hide-in-submode;
          tailf:cli-no-name-on-delete;
          type empty;
        }
        leaf p2mp-lsp {
          tailf:cli-hide-in-submode;
          tailf:cli-no-name-on-delete;
          type empty;
        }
        leaf mpls-tp {
          tailf:cli-hide-in-submode;
          tailf:cli-no-name-on-delete;
          tailf:cli-no-value-on-delete;
          type uint16 {
            range "1..61440";
          }
        }

        // router * / mpls / lsp * / to
        leaf to {
          tailf:info "IP address of the egress router for the LSP";
          type inet:ipv4-address;
        }

        // router * / mpls / lsp * / fast-reroute /
        container fast-reroute {
          tailf:info "Configure fast reroute for LSP";
          tailf:cli-add-mode;
          tailf:cli-embed-no-on-delete;

          // router * / mpls / lsp * / fast-reroute / frr-method
          leaf frr-method {
            tailf:info "<frr-method>;;one-to-one|facility";
            tailf:cli-hide-in-submode;
            tailf:cli-drop-node-name;
            type enumeration {
              enum facility;
              enum one-to-one;
            }
          }

          // router * / mpls / lsp * / fast-reroute / hop-limit
          leaf hop-limit {
            tailf:info "Configure hop limit  for fast reroute";
            tailf:cli-embed-no-on-delete;
            type empty;
          }

          // router * / mpls / lsp * / fast-reroute / node-protect
          leaf node-protect {
            tailf:info "Configure node protect";
            tailf:cli-embed-no-on-delete;
            type empty;
          }
        }

        // router * / mpls / lsp * / primary /
        container primary {
          tailf:info "Configure a preferred path for the LSP";
          tailf:cli-add-mode;
          tailf:cli-embed-no-on-delete;

          // router * / mpls / lsp * / primary / path
          leaf path {
            tailf:cli-drop-node-name;
            tailf:cli-hide-in-submode;
            tailf:non-strict-leafref {
              path "/alu:router/mpls/path/name";
            }
            type string;
          }

          // router * / mpls / lsp * / primary / adaptive
          leaf adaptive {
            tailf:info "Enable/Disable make-before-break functionality";
            tailf:cli-embed-no-on-delete;
            type empty;
          }
        }


        // router * / mpls / lsp * / secondary
        container secondary {
          tailf:cli-add-mode;

          // router * / mpls / lsp * / secondary / path
          leaf path {
            tailf:cli-drop-node-name;
            tailf:cli-hide-in-submode;
            tailf:non-strict-leafref {
              path "/alu:router/mpls/path/name";
            }
            type string;
          }

          // router * / mpls / lsp * / secondary / adaptive
          leaf adaptive {
            tailf:cli-embed-no-on-delete;
            type empty;
          }
        }

        // router * / mpls / lsp * / cspf
        leaf cspf {
          tailf:info "Enable/disable CSPF support for the LSP";
          tailf:cli-embed-no-on-delete;
          type empty;
        }

        // router * / mpls / lsp * / shutdown
        leaf shutdown {
          tailf:info "Administratively enable/disable the LSP";
          tailf:cli-show-no;
          type empty;
        }
      }

      // router * / mpls / static-lsp *
      list static-lsp {
        tailf:info "Configure a static LSP on the ingress router";
        tailf:cli-embed-no-on-delete;
        key name;
        leaf name {
          type string;
        }

        // router * / mpls / static-lsp * / push
        container push {
          tailf:info "Label to be pushed on the label stack and the"
                    +" next hop IP address";
          tailf:cli-compact-syntax;
          tailf:cli-sequence-commands;

          leaf label {
            tailf:cli-drop-node-name;
            type union {
              type uint32 {
                range "16..1048575";
              }
              type enumeration {
                enum "implicit-null-label";
              }
            }
          }

          leaf nexthop {
            type inet:ipv4-address;
          }
        }

        // router * / mpls / static-lsp * / to
        leaf to {
          tailf:info "IP address of the egress router for the static LSP";
          tailf:cli-no-name-on-delete;
          tailf:cli-no-value-on-delete;
          type inet:ipv4-address;
        }

        // router * / mpls / static-lsp * / shutdown
        leaf shutdown {
           tailf:info "Administratively enable/disable the static LSP";
           tailf:cli-boolean-no;
           default true;
           type boolean;
        }
      }

      // router * / mpls / shutdown
      leaf shutdown {
        tailf:info "Administratively enable/disable the MPLS instance";
        tailf:cli-boolean-no;
        default true;
        type boolean;
      }
    }

      // router * / rsvp
    container rsvp {
      tailf:info "Create/Configure or delete RSVP instance";
      tailf:cli-embed-no-on-delete;
      tailf:cli-recursive-delete;
      tailf:cli-add-mode;
      tailf:cli-diff-dependency "../mpls";
      must "../mpls";
      presence present;

      // router * / rsvp / interface *
      list interface {
        tailf:info "Configure RSVP on an IP interface";
        tailf:cli-embed-no-on-delete;
        tailf:cli-diff-dependency "/alu:router/mpls/interface/name";
        key name;
        leaf name {
          tailf:non-strict-leafref {
            path "/alu:router/interface/interface-name";
          }
          type string;
        }

        // router * / rsvp / interface * / refresh-reduction /
        container refresh-reduction {
          tailf:info "Enable/Disable RSVP overhead refresh reduction";
          tailf:cli-embed-no-on-delete;
          tailf:cli-add-mode;

          // router * / rsvp / interface * / refresh-reduction /
          // reliable-delivery
          leaf reliable-delivery {
            tailf:info "Enable/Disable reliable delivery of RSVP messages";
            tailf:cli-embed-no-on-delete;
            type empty;
          }
        }

        // router * / rsvp / interface * / authentication-key
        container authentication-key {
          tailf:info "Configure the RSVP authentication key for all peers";
          tailf:cli-embed-no-on-delete;
          tailf:cli-compact-syntax;
          tailf:cli-sequence-commands;

          leaf key {
            tailf:cli-drop-node-name;
            tailf:cli-no-value-on-delete;
            type string;
          }

          leaf type {
            tailf:cli-drop-node-name;
            tailf:cli-no-value-on-delete;
            type enumeration {
              enum hash;
              enum hash2;
            }
          }
        }

        // router * / rsvp / interface * /
        leaf shutdown {
          tailf:info "Administratively enable/disable RSVP on the interface";
          tailf:cli-boolean-no;
          default false;
          type boolean;
        }
      }

      // router * / rsvp / shutdown
      leaf shutdown {
        tailf:info "Administratively enable/disable the RSVP instance";
        tailf:cli-boolean-no;
        default true;
        type boolean;
      }
    }

    // router * / router-advertisement
    container router-advertisement {
      tailf:cli-add-mode;
      tailf:cli-diff-dependency "/alu:service/ies";

      // router * / router-advertisement / interface *
      list interface {
        tailf:info "Configure router advertisement properties"
        + " on an interface";
        tailf:cli-embed-no-on-delete;
        key ip-int-name;
        leaf ip-int-name {
          type string;
          tailf:non-strict-leafref {
            path "/alu:router/interface/interface-name";
          }
        }

        // router * / router-advertisement / interface * /
        // current-hop-limit
        leaf current-hop-limit {
          tailf:info "Configure the router to advertise the hop-limit";
          tailf:cli-no-value-on-delete;
          type uint8;
        }

        // router * / router-advertisement / interface * /
        // max-advertisement-interval
        leaf max-advertisement-interval {
          tailf:info "Configure max interval between sending ICMPv6";
          tailf:cli-no-value-on-delete;
          type uint16 {
            range "4..1800";
          }
        }

        // router * / router-advertisement / interface * /
        // min-advertisement-interval
        leaf min-advertisement-interval {
          tailf:info "Configure min interval between sending ICMPv6";
          tailf:cli-no-value-on-delete;
          type uint16 {
            range "3..1350";
          }
        }

        // router * / router-advertisement / interface * / mtu
        leaf mtu {
          tailf:info "Configure the MTU for sending packets to the router";
          tailf:cli-no-value-on-delete;
          type uint16 {
            range "1280..9212";
          }
        }

        // router * / router-advertisement / interface * /
        // managed-configuration
        leaf managed-configuration {
          tailf:info "Configure the managed-config-flag to be advertised";
          type empty;
        }

        // router * / router-advertisement / interface * /
        // other-stateful-configuration
        leaf other-stateful-configuration {
          tailf:info "Configure the other-config-flag to be advertised";
          type empty;
        }

        // router * / router-advertisement / interface * / prefix *
        list prefix {
          tailf:info "Configure prefix that needs to be included";
          tailf:cli-embed-no-on-delete;
          key ipv6-prefix;
          leaf ipv6-prefix {
            type inet:ipv6-prefix;
          }
        }

        // router * / router-advertisement / interface * / reachable-time
        leaf reachable-time  {
          tailf:info "Configure how long this router should be reachable";
          tailf:cli-no-value-on-delete;
          type uint32 {
            range "0..3600000";
          }
        }

        // router * / router-advertisement / interface * / retransmit-time
        leaf retransmit-time {
          tailf:info "Configure the time interval to be advertised";
          tailf:cli-no-value-on-delete;
          type uint32 {
            range "0..1800000";
          }
        }

        // router * / router-advertisement / interface * / router-lifetime
        leaf router-lifetime {
          tailf:info "Configure the lifetime value that the router advertises";
          tailf:cli-no-value-on-delete;
          type uint16 {
            range "0..9000";
          }
        }

        // router * / router-advertisement / interface * / use-virtual-mac
        leaf use-virtual-mac {
          tailf:info "Send Router Advertisement messages using VRRP";
          type empty;
        }

        // router * / router-advertisement / interface * / shutdown
        leaf shutdown {
          tailf:info "Command to disable router advertisement on an interface";
          tailf:cli-boolean-no;
          default true;
          type boolean;
        }
      }
    }

    // router * / mld /
    container mld {
      tailf:cli-add-mode;
      tailf:cli-diff-dependency "/alu:service/ies";

      // router * / mld / interface *
      list interface {
        tailf:cli-embed-no-on-delete;
        key ip-int-name;
        leaf ip-int-name {
          type string;
          tailf:non-strict-leafref {
            path "/alu:router/interface/interface-name";
          }
        }

        // router * / mld / interface * / shutdown
        leaf shutdown {
          tailf:cli-boolean-no;
          default true;
          type boolean;
        }
      }

      // router * / mld / shutdown
      leaf shutdown {
        tailf:cli-boolean-no;
        default true;
        type boolean;
      }
    }

    // router * / policy-options
    container policy-options {
      tailf:cli-embed-no-on-delete;
      tailf:cli-recursive-delete;
      tailf:cli-explicit-exit;
      tailf:cli-add-mode;

      // router * / policy-options / begin
      container begin {
        tailf:info "Switch to edit mode for route policies";
        tailf:cli-add-mode;
        tailf:cli-exit-command "commit";
        tailf:cli-recursive-delete;

        // router * / policy-options / begin / prefix-list
        list prefix-list {
          tailf:cli-embed-no-on-delete;
          key name;
          leaf name {
            type string;
          }

          // router * / policy-options / begin / prefix-list * / prefix *
          list prefix {
            tailf:cli-suppress-mode;
            tailf:cli-compact-syntax;
            tailf:cli-embed-no-on-delete;
            key ip-prefix;
            leaf ip-prefix {
              type union {
                type tailf:ipv4-address-and-prefix-length;
                type tailf:ipv6-address-and-prefix-length;
              }
            }

            choice a {
              leaf exact {
                type empty;
              }

              leaf longer {
                type empty;
              }

              leaf through {
                type uint8 {
                  range "0..128";
                }
              }
              leaf prefix-length-range {
                type string;
              }
            }
          }
        }

        // router * / policy-options / begin / community *
        list community {
          tailf:info "Create/delete a community list for use in"
          + " route policy entries";
          tailf:cli-compact-syntax;
          tailf:cli-suppress-mode;
          key name;
          leaf name {
            type string;
          }

          choice community-choice {
            case a {
              leaf-list members {
                tailf:cli-flat-list-syntax;
                tailf:cli-no-name-on-delete;
                tailf:cli-no-value-on-delete;
                type string {
                  length "1..72";
                }
              }
            }
            case b {
              leaf expression {
                type string {
                  length "1..900";
                }
              }
            }
          }
        }

        // router * / policy-options / begin / damping
        list damping {
          tailf:info "Configure a damping profile for use in"
            +" route policy entries";
          tailf:cli-embed-no-on-delete;
          key name;
          leaf name {
            type string {
              length "1..32";
            }
          }

          // router * / policy-options / begin / half-life
          leaf half-life  {
            tailf:info "The time in minutes after which the accumulated"
              + " figure-of-merit value is reduced by half if the"
              + " route remains stable.";
            tailf:cli-no-value-on-delete;
            type uint8 {
              range "1..45";
            }
          }

          // router * / policy-options / begin / max-supress
          leaf max-suppress {
            tailf:info "The maximum time in minutes that a route can be"
              +" suppressed no matter how unstable it has been.";
            tailf:cli-no-value-on-delete;
            type uint16 {
              range "1..720";
            }
          }

          // router * / policy-options / begin / reuse
          leaf reuse {
            tailf:info "The figure-of-merit value below which a suppressed
                        route can be used again.";
            tailf:cli-no-value-on-delete;
            type uint32 {
              range "1..20000";
            }
          }

          // router * / policy-options / begin / supress
          leaf suppress {
            tailf:info "The figure-of-merit value above which a route is"
              + " suppressed for use or inclusion in route advertisements.";
            tailf:cli-no-value-on-delete;
            type uint32 {
              range "1..20000";
            }
          }
        }

        // router * / policy-options / begin / policy-statement
        list policy-statement {
          tailf:info "Configuring a route policy statement";
          tailf:cli-embed-no-on-delete;
          tailf:cli-recursive-delete;
          key name;
          leaf name {
            type string;
          }

          // router * / policy-options / begin /
          // policy-statement * / default-action
          container default-action {
            tailf:info "Configuring actions for routes that do not match"
                      +" any policy entries";
            uses policy-options-action-grouping;
          }

          // router * / policy-options / begin /
          // policy-statement * / entry *
          list entry {
            tailf:info "Configure a route policy entry within the"
              +" policy statement";
            tailf:cli-embed-no-on-delete;
            key id;
            leaf id {
              type uint32 {
                range "1..4294967295";
              }
            }

            // router * / policy-options / begin /
            // policy-statement * / entry * / description
            leaf description {
              tailf:info "Textual description for the policy statement";
              tailf:cli-embed-no-on-delete;
              tailf:cli-no-value-on-delete;
              type string {
                length "1..80";
              }
            }

            // router * / policy-options / begin /
            // policy-statement * / entry * / action /
            container action {
              tailf:info "Configure actions to take for routes"
                       + " matching a policy entry";
              uses policy-options-action-grouping;
            }

            // router * / policy-options / begin /
            // policy-statement * / entry * / action / from /
            container from {
              tailf:info "Configure policy match criteria based on source"
                + " of routes or protocol from which it is received";
              tailf:cli-embed-no-on-delete;
              tailf:cli-add-mode;

              // router * / policy-options / begin /
              // policy-statement * / entry * / action / from / area
              leaf area {
                tailf:info "Configure an OSPF area as a match criterion"
                  + " for the entry";
                tailf:cli-no-value-on-delete;
                type union {
                  type inet:ipv4-address;
                  type uint32 {
                    range "0..4294967295";
                  }
                }
              }

              // router * / policy-options / begin /
              // policy-statement * / entry * / action / from / as-path
              leaf as-path {
                tailf:info "Configures an AS Path regular expression statement"
                  + " as a match criterion for the entry";
                tailf:cli-no-value-on-delete;
                type string {
                  length "1..32";
                }
              }

              // router * / policy-options / begin /
              // policy-statement * / entry * / action / from / as-path-group
              leaf as-path-group {
                tailf:info "Configures an AS Path Group as a match criterion"
                  +" for the entry";
                tailf:cli-no-value-on-delete;
                type string {
                  length "1..32";
                }
              }

              // router * / policy-options / begin /
              // policy-statement * / entry * / action / from / community
              leaf community {
                tailf:info "Configure a community list as a match criterion"
                  + " for the entry";
                tailf:cli-no-value-on-delete;
                type string {
                  length "1..32";
                }

              }

              // router * / policy-options / begin /
              // policy-statement * / entry * / action / from / external
              leaf external {
                tailf:info "Configure external ISIS route matching criterion"
                  + " for the entry";
                type empty;
              }

              // router * / policy-options / begin /
              // policy-statement * / entry * / action / from / family
              leaf-list family {
                tailf:info "Configure the address families that this condition"
                  + " would match against";
                tailf:cli-no-value-on-delete;
                tailf:cli-flat-list-syntax;
                type enumeration {
                  enum ipv4;
                  enum ipv6;
                  enum mcast-ipv4;
                  enum mcast-ipv6;
                  enum vpn-ipv4;
                  enum vpn-ipv6;
                  enum l2-vpn;
                  enum mvpn-ipv4;
                  enum flow-ipv4;
                  enum ms-pw;
                  enum mdt-safi;
                  enum route-target;
                  enum mcast-vpn-ipv4;
                  enum mvpn-ipv6;
                  enum flow-ipv6;
                }
              }

              // router * / policy-options / begin /
              // policy-statement * / entry * / action / from / group-address
              leaf group-address {
                tailf:info "Configure a prefix list of multicast group address"
                  + " as a match criterion for the entry";
                tailf:cli-no-value-on-delete;
                type string {
                  length "1..32";
                }
              }

              // router * / policy-options / begin /
              // policy-statement * / entry * / action / from / host-ip
              leaf host-ip {
                tailf:info "Configure a prefix list of IGMP host ip address as"
                  + " a match criterion for this entry";
                tailf:cli-no-value-on-delete;
                type string {
                  length "1..32";
                }
              }

              // router * / policy-options / begin /
              // policy-statement * / entry * / action / from / interface
              leaf interface {
                tailf:info "Configure the name of the interface as a match"
                  + " criterion for this entry";
                tailf:cli-no-value-on-delete;
                type string {
                  length "1..32";
                }
              }

              // router * / policy-options / begin /
              // policy-statement * / entry * / action / from / level
              leaf level {
                tailf:info "Configure ISIS route level as a match criterion"
                  +" for the entry";
                tailf:cli-no-value-on-delete;
                type uint8 {
                  range "1..2";
                }
              }

              // router * / policy-options / begin /
              // policy-statement * / entry * / action / from / neighbor
              container neighbor {
                tailf:info "Configure a neighbor or prefix list as match "
                          +"criterion for the entry";
                tailf:cli-embed-no-on-delete;
                choice a {
                  leaf ip-address {
                    tailf:cli-drop-node-name;
                    tailf:cli-no-value-on-delete;
                    type inet:ipv4-address;
                  }
                  leaf prefix-list {
                    tailf:cli-no-name-on-delete;
                    tailf:cli-no-value-on-delete;
                    type string;
                  }
                }
              }

              // router * / policy-options / begin /
              // policy-statement * / entry * / action / from / origin
              leaf origin {
                tailf:info "Configure a BGP or Subscriber Management origin"
                  +" attribute as a match criterion for the entry";
                tailf:cli-no-value-on-delete;
                type enumeration {
                  enum igp;
                  enum egp;
                  enum incomplete;
                  enum any;
                  enum aaa;
                  enum dhcp;
                  enum ludb;
                }
              }

              // router * / policy-options / begin /
              // policy-statement * / entry * / action / from / policy
              leaf policy {
                tailf:info "Configures a policy statement as a match criterion"
                  +" for the entry";
                tailf:cli-no-value-on-delete;
                type string {
                  length "1..32";
                }
              }

              // router * / policy-options / begin /
              // policy-statement * / entry * / action / from / prefix-list
              leaf-list prefix-list {
                tailf:info "Configure a prefix list as a match criterion"
                  +" for the entry";
                tailf:cli-flat-list-syntax;
                type string {
                  length "1..32";
                }
              }

              // router * / policy-options / begin /
              // policy-statement * / entry * / action / from / protocol
              leaf protocol {
                tailf:info "Configure a routing protocol as a match criterion"
                  +" for the entry";
                tailf:cli-no-value-on-delete;
                type enumeration {
                  enum direct;
                  enum static;
                  enum bgp;
                  enum isis;
                  enum ospf;
                  enum rip;
                  enum aggregate;
                  enum bgp-vpn;
                  enum igmp;
                  enum pim;
                  enum ospf3;
                  enum ldp;
                  enum sub-mgmt;
                  enum mld;
                  enum managed;
                  enum vpn-leak;
                  enum tms;
                  enum nat;
                  enum periodic;
                  enum ipsec;
                  enum mpls;
                  enum dhcpv6-pd;
                  enum dhcpv6-na;
                  enum dhcpv6-ta;
                  enum dhcpv6-pd-excl;
                }
              }

              // router * / policy-options / begin /
              // policy-statement * / entry * / action / from / source-address
              leaf source-address {
                tailf:info "Configure a multicast data source"
                  +" address as a match criterion for this entry";
                tailf:cli-no-value-on-delete;
                type union {
                  type inet:ipv4-address;
                  type inet:ipv6-address;
                }
              }

              // router * / policy-options / begin /
              // policy-statement * / entry * / action / from /  state
              leaf state {
                tailf:info "Configure a state as a match criterion"
                + " for the entry";
                tailf:cli-no-value-on-delete;
                type enumeration {
                  enum srrp-master;
                  enum srrp-non-master;
                  enum ipsec-master-with-peer;
                  enum ipsec-non-master;
                  enum ipsec-master-without-peer;
                }
              }

              // router * / policy-options / begin /
              // policy-statement * / entry * / action / from / tag
              leaf tag {
                tailf:info "Configure a route tag as a match criterion"
                  + "for the entry";
                tailf:cli-no-value-on-delete;
                type uint32;
              }

              // router * / policy-options / begin /
              // policy-statement * / entry * / action / from / type
              leaf type {
                tailf:info "Configure an OSPF type metric as a match criterion"
                  + "for the entry";
                tailf:cli-no-value-on-delete;
                type uint8 {
                  range "1..2";
                }
              }
            }

            // router * / policy-options / begin /
            // policy-statement * / entry * / action / to
            container to {
              tailf:info "Configure policy match criteria based on destination"
                + " of routes or protocol into which it is advertised";
              tailf:cli-embed-no-on-delete;
              tailf:cli-add-mode;

              // router * / policy-options / begin /
              // policy-statement * / entry * / action / to / level
              leaf level {
                tailf:info "Configure ISIS route level as a match criterion"
                  +" for the entry";
                tailf:cli-no-value-on-delete;
                type uint8 {
                  range "1..2";
                }
              }

              // router * / policy-options / begin /
              // policy-statement * / entry * / action / to / neighbor
              leaf neighbor {
                tailf:info "Configure a neighbor or prefix list as match"
                  + "criterion for the entry";
                tailf:cli-no-value-on-delete;
                type union {
                  type inet:ipv4-address;
                  type inet:ipv6-address;
                  type string {
                    length "1..32";
                  }
                }
              }

              // router * / policy-options / begin /
              // policy-statement * / entry * / action / to / prefix-list
              leaf-list prefix-list {
                tailf:info "Configure a prefix list as a match criterion"
                  +" for the entry";
                 tailf:cli-flat-list-syntax;
                type string {
                  length "1..32";
                }
              }

              // router * / policy-options / begin /
              // policy-statement * / entry * / action / to / protocol
              leaf protocol {
                tailf:info "Configure a routing protocol as a match criterion"
                  +" for the entry";
                tailf:cli-no-value-on-delete;
                type enumeration {
                  enum direct;
                  enum static;
                  enum bgp;
                  enum isis;
                  enum ospf;
                  enum rip;
                  enum aggregate;
                  enum bgp-vpn;
                  enum igmp;
                  enum pim;
                  enum ospf3;
                  enum ldp;
                  enum sub-mgmt;
                  enum mld;
                  enum managed;
                  enum vpn-leak;
                  enum tms;
                  enum nat;
                  enum periodic;
                  enum ipsec;
                  enum mpls;
                  enum dhcpv6-pd;
                  enum dhcpv6-na;
                  enum dhcpv6-ta;
                  enum dhcpv6-pd-excl;
                }
              }
            }
          }
        }

        // router * / policy-options / as-path
        list as-path {
          tailf:info "Create/delete AS Path regular expressions"
                    +" for use in route policy entries";
          tailf:cli-compact-syntax;
          key name;
          leaf name {
            type string;
          }

          // router * / policy-options / as-path / regexp
          leaf regexp {
            tailf:cli-drop-node-name;
            type string;
          }
        }
      }
    }
    // router * / pim
    container pim {
      tailf:info "Create/Configure or delete PIM instance";
      tailf:cli-add-mode;
      presence present;

      // router * / pim / interface *
      list interface {
        tailf:info "Configure PIM interface";
        key ip-int-name;
        leaf ip-int-name {
          type leafref {
            path "/alu:router/interface/interface-name";
          }
        }

        // router * / pim / interface * / assert-period
        leaf assert-period {
          tailf:info "Configure the period for periodic refreshes of PIM"+
                     " Assert messages on an interface";
          tailf:cli-no-value-on-delete;
          type uint16 {
            range "1..300";
          }
        }

        // router * / pim / interface * / bfd-enable
         leaf bfd-enable {
           tailf:info "Enable BFD";
           type enumeration {
             enum "ipv4";
             enum "ipv6";
           }
         }

        // router * / pim / interface * / bsm-check-rtr-alert
         leaf bsm-check-rtr-alert {
           tailf:info "Enable/disable accepting of BSM packets "
                      +"without router alert option";
           type empty;
         }

        // router * / pim / interface * / hello-interval
         leaf hello-interval {
           tailf:info "Configure the frequency at which PIM hello messages"+
                      " are sent over this interface";
           tailf:cli-no-value-on-delete;
          type uint8;
        }

        // router * / pim / interface * / hello-multiplier
        leaf hello-multiplier {
          tailf:info "Configure hello-multiplier in multiples of 0.1 "
                     +"(deci-units)";
          tailf:cli-no-value-on-delete;
          type uint8 {
            range "20..100";
          }
        }

        // router * / pim / interface * / improved-assert
        leaf improved-assert {
          tailf:info "Enable/disable improved assert processing";
          type empty;
        }

        // router * / pim / interface * / instant-prune-echo
        leaf instant-prune-echo {
          tailf:info "Enable/Disable instant PruneEcho for a PIM interface";
          type empty;
        }

        // router * / pim / interface * / ipv4-multicast-disable
         leaf ipv4-multicast-disable {
           tailf:info "Administratively disable/enable PIM operation for "+
                      "IPv4 on this interface";
           type empty;
         }

        // router * / pim / interface * / ipv6-multicast-disable
        leaf ipv6-multicast-disable {
          tailf:info "Administratively disable/enable PIM operation for"
                    +" IPv6 on this interface";
          type empty;
        }

        // router * / pim / interface * / max-groups
         leaf max-groups {
           tailf:info "Configure the maximum number of groups for this "
                      +"interface";
           tailf:cli-no-value-on-delete;
           type uint16 {
             range "1..16000";
           }
         }

         // router * / pim / interface * / mac /
        container mcac {
          tailf:info "Configure multicast CAC policy and constraints"
                   +" for this interface";
          tailf:cli-add-mode;

          // router * / pim / interface * / mac / mc-constraints
          container mc-constraints {
            tailf:info "Create context that allows for the configuration of"+
                       " the different levels and their associated bandwidth"+
                       " for multicast cac policy on this interface";
            tailf:cli-add-mode;

            container level {
              tailf:info "Configure levels and their associated bandwidth"
                        +" for multicast cac policy on this interface";
              tailf:cli-embed-no-on-delete;
              tailf:cli-sequence-commands;

              leaf level-id{
                tailf:cli-drop-node-name;
                tailf:cli-no-value-on-delete;
                type uint8 {
                  range "1..8";
                }
              }

              leaf bw {
                tailf:cli-optional-in-sequence;
                tailf:cli-no-name-on-delete;
                tailf:cli-no-value-on-delete;
                type enumeration {
                  enum "kbps";
                }
              }
            }

            // router * / pim / interface * / mac / number-down *
             list number-down {
               tailf:info "Configure number of ports down along with "+
                          "level for multicast cac policy on this"+
                          " interface";
               tailf:cli-suppress-mode;
               key number-lag-port-down;
               leaf number-lag-port-down {
                 type uint8 {
                   range "1..64";
                 }
               }

              // router * / pim / interface * / mac / number-down * level-id
               leaf level-id {
                tailf:cli-drop-node-name;
                tailf:cli-no-value-on-delete;
                type uint8 {
                  range "1..8";
                }
              }
            }

            // router * / pim / interface * / mac / number-down *
            // use-lag-port-weight
            leaf use-lag-port-weight {
              tailf:info "Enable/disable using the LAG port weight while"+
                        " calculating Multicast CAC constraints";
              type empty;
            }

            // router * / pim / interface * / mac / number-down * shutdown
            leaf shutdown {
              tailf:info "Administratively enable/disable constraint"
                         +" for multicast cac policy";
              tailf:cli-boolean-no;
              default true;
              type boolean;
             }
          }

          // router * / pim / interface * / policy
           leaf policy {
             tailf:info "Configure multicast CAC policy name";
             tailf:cli-no-value-on-delete;
             type string {
               length "1..32";
             }
           }

          // router * / pim / interface * / unconstrained-bw
          container unconstrained-bw {
            tailf:info "Configure unconstrained-bw for multicast "+
                        "cac policy on this interface";
            tailf:cli-embed-no-on-delete;
            tailf:cli-sequence-commands;

            leaf bandwidth {
              tailf:cli-drop-node-name;
              tailf:cli-no-value-on-delete;
              type uint32 {
                range "0..2147483647";
              }
            }

            leaf mandatory-bw {
              tailf:cli-no-name-on-delete;
              tailf:cli-no-value-on-delete;
              type uint32 {
                range "0..2147483647";
              }
            }
          }
        }

        // router * / pim / interface * / multicast-senders
         leaf multicast-senders {
           tailf:info "Configure the way subnet matching is done for incoming"
                    + " data packets on this interface";
           tailf:cli-no-value-on-delete;
           type enumeration {
             enum auto;
             enum always;
             enum never;
           }
         }

        // router * / pim / interface * / p2mp-ldp-tree-join
        leaf p2mp-ldp-tree-join {
          tailf:info "Enable/Disable p2mp-ldp-tree-join";
          type enumeration {
            enum ipv4;
            enum ipv6;
          }
        }

        // router * / pim / interface * / priority
         leaf priority {
           tailf:info "Configure the DR election priority for this interface";
           tailf:cli-no-value-on-delete;
           type uint32;
         }

        // router * / pim / interface * / sticky-dr
        container sticky-dr {
          tailf:info "Enable/disable sticky-DR and configure DR"
                    +" priority for sticky-DR";
          tailf:cli-embed-no-on-delete;

          leaf priority {
            tailf:cli-no-name-on-delete;
            tailf:cli-no-value-on-delete;
            type uint32;
          }

          // router * / pim / interface * / sticky-dr priority
           leaf three-way-hello {
             tailf:info "Configure compatibility mode for three-way-hello";
             type empty;
           }

          // router * / pim / interface * / sticky-dr tracking-support
           leaf tracking-support {
             tailf:info "Enable/disable tracking support";
             type empty;
           }
        }

        // router * / pim / interface * / shutdown
        leaf shutdown {
          tailf:info "Administratively enable/disable the interface";
          tailf:cli-boolean-no;
          default true;
          type boolean;
        }
      }

      // router * / pim / ipv4-multicast-disable
      leaf ipv4-multicast-disable {
        tailf:info "Administratively disable/enable PIM operation for IPv4";
        type empty;
      }

       // router * / pim / ipv6-multicast-disable
      leaf ipv6-multicast-disable {
        tailf:info "Administratively disable/enable PIM operation for IPv6";
        type empty;
      }

      // router * / pim / rp
      container rp {
        tailf:info "Configure the router as static or Candidate-RP";
        tailf:cli-add-mode;
        list anycast {
          tailf:info "Configure PIM anycast protocol instance for the RP";
          key rp-ip-address;
          leaf rp-ip-address {
            type inet:ipv4-address;
          }
          list rp-set-peer {
            tailf:cli-suppress-mode;
            tailf:info "Configure a peer in the anycast rp-set";
            key ip-address;
            leaf  ip-address{
              tailf:cli-drop-node-name;
              type inet:ipv4-address;
            }
          }
        }
        // router * / pim / rp / static
        container static {
          tailf:info "Context to configure static group to RP mapping";
          tailf:cli-add-mode;
          presence true;
          // router * / pim / rp / static / address * /
          list address {
            tailf:info "Configure the RP address for multicast group prefixes";
            key ip-address;
            leaf ip-address {
              tailf:cli-drop-node-name;
              type union {
                type inet:ipv4-address;
                type inet:ipv6-address;
              }
            }
            // router * / pim / rp / static / address * / group-prefix *
            list group-prefix {
              tailf:cli-suppress-mode;
              tailf:info "Configure a group prefix for the RP address";
              key grp-ip-addr;
              leaf grp-ip-addr {
                tailf:cli-drop-node-name;
                type tailf:ipv4-address-and-prefix-length;
              }
            }
          }
        }
        // router * / pim / rp / bsr-candidate
        container bsr-candidate {
          tailf:info "Context to configure Candidate Bootstrap parameters";
          tailf:cli-add-mode;
          leaf shutdown {
            tailf:info "Administratively enable/disable participation of"
                      +" the router in bootstrap election";
            tailf:cli-boolean-no;
            default true;
            type boolean;
          }
        }
        // router * / pim / rp / rp-candidate
        container rp-candidate {
          tailf:info "Context to configure the Candidate RP parameters";
          tailf:cli-add-mode;
          leaf shutdown {
            tailf:info "Administratively enable/disable the Candidate-RP";
            tailf:cli-boolean-no;
            default true;
            type boolean;
          }
        }
      }

       // router * / pim / shutdown
      leaf shutdown {
        tailf:info "Administratively enable or disable the operation of PIM";
        tailf:cli-boolean-no;
        default false;
        type boolean;
      }
    }
  }

  /// ========================================================================
  /// system /
  /// ========================================================================
  container system {
    tailf:info "Configure system parameters";
    tailf:cli-recursive-delete;
    tailf:cli-add-mode;

    // system / alarms
    container alarms {

      // system / alarms max-cleared
      leaf max-cleared {
        type string;
      }

      // system / alarms shutdown
      leaf shutdown {
        tailf:cli-boolean-no;
        default true;
        type boolean;
      }
    }

    // system / atm
    container atm {

      // system / atm atm-location-id
      leaf atm-location-id {
        type string;
      }

      // system / atm oam
      container oam {

        // system / atm oam loopback-period
        leaf loopback-period {
          type string;
        }

        // system / atm oam retry-down
        leaf retry-down {
          type string;
        }

        // system / atm oam retry-up
        leaf retry-up {
          type string;
        }
      }
    }

    // system / boot-bad-exex
    leaf boot-bad-exec {
      type string;
    }

    // system / boot-good-exex
    leaf boot-good-exec {
      type string;
    }

    // system / chassis-mode *
    list chassis-mode {
      tailf:cli-recursive-delete;
      tailf:cli-embed-no-on-delete;
      key chassis-mode;
      leaf chassis-mode {
        type string;
      }

      // system / chassis-mode * / force
      leaf force {
        tailf:cli-hide-in-submode;
        type empty;
      }

      // system / chassis-mode * / power-supply *
      list power-supply {
        tailf:cli-embed-no-on-delete;
        tailf:cli-suppress-mode;
        key "power-supply-id power-supply-type";
        leaf power-supply-id {
          type string;
        }

        leaf power-supply-type {
          type enumeration {
            enum dc;
          }
        }
      }
    }

    // system / clli-code
    leaf clli-code {
      type string;
    }

    // system / config-backup
    leaf config-backup {
      type string;
    }

    // system / contact
    leaf contact {
      type string;
    }

    // system / coordinates
    leaf coordinates {
      type string;
    }



    // system / dns
    container dns {
      tailf:cli-add-mode;

      // system / dns address-pref
      container address-pref {
        choice choice {

          // system / dns address-pref ipv4-only
          leaf ipv4-only {
            type empty;
          }

          // system / dns address-pref ipv6-first
          leaf ipv6-first {
            type empty;
          }
        }
      }
    }

    // system / enable-icmp-vse
    leaf enable-icmp-vse {
      type empty;
    }

    // system / ethernet
    container ethernet {
      tailf:info "Configure system-wide Ethernet parameters";
      tailf:cli-add-mode;

      // system / ethernet / efm-oam
      container efm-oam {

        // system / ethernet / efm-oam grace-tx-enable
        leaf grace-tx-enable {
          type empty;
        }
      }

      // system / ethernet / new-qinq-untagged-sap
      leaf new-qinq-untagged-sap {
        tailf:info "Configure Q-IN-Q behavior";
        type empty;
      }
    }

    // system / ethernet l4-load-balancing
    leaf l4-load-balancing {
      type empty;
    }

    // system / ethernet lacp-system-priority
    leaf lacp-system-priority {
      type string;
    }

    // system / lldp
    container lldp {
      tailf:cli-add-mode;

      // system / lldp message-fast-tx
      leaf message-fast-tx {
        type string;
      }

      // system / lldp message-fast-tx-init
      leaf message-fast-tx-init {
        type string;
      }

      // system / lldp reinit-delay
      leaf reinit-delay {
        type string;
      }

      // system / lldp tx-credit-max
      leaf tx-credit-max {
        type string;
      }

      // system / lldp tx-hold-multiplier
      leaf tx-hold-multiplier {
        type string;
      }

      // system / lldp tx-interval
      leaf tx-interval {
        type string;
      }

      // system / lldp notification-interval
      leaf notification-interval {
        type string;
      }

      // system / lldp shutdown
      leaf shutdown {
        tailf:cli-boolean-no;
        default true;
        type boolean;
      }
    }

    // system / location
    leaf location {
      type string;
    }

    // system / login-control /
    container login-control {
      tailf:cli-add-mode;

      // system / login-control /  exponential-backoff
      leaf exponential-backoff {
        type empty;
      }

      // system / login-control / ftp
      container ftp {
        tailf:cli-add-mode;

        // system / login-control / ftp incound-max-sessions
        leaf inbound-max-sessions {
          type string;
        }
      }

      // system / login-control / idle-timeout
      leaf idle-timeout {
        type string;
      }

      // system / login-control / idle-timeoutdisable
      leaf idle-timeoutdisable {
        type empty;
      }

      // system / login-control / login-banner
      leaf login-banner {
        type empty;
      }

      // system / login-control / motd
      container motd {
        choice choice {

          // system / login-control / motd url
          leaf url {
            type string;
          }

          // system / login-control / motd text
          leaf text {
            type string;
          }
        }
      }

      // system / login-control / pre-login-message
      container pre-login-message {
        presence present;
        tailf:cli-sequence-commands;
        tailf:cli-compact-syntax;
        tailf:cli-full-no;
        //tailf:cli-recursive-delete;
        tailf:cli-embed-no-on-delete;

        // system / login-control / pre-login-message login-text-string
        leaf login-text-string {
          tailf:cli-drop-node-name;
          tailf:cli-delete-container-on-delete;
          //mandatory true;
          type string;
        }

        // system / login-control / pre-login-message name
        leaf name {
          tailf:cli-no-name-on-delete;
          type empty;
        }
      }

      // system / login-control / ssh
      container ssh {
        tailf:cli-add-mode;

        // system / login-control / ssh disable-graceful-shutdown
        leaf disable-graceful-shutdown {
          type empty;
        }

        // system / login-control / ssh inbound-max-sessions
        leaf inbound-max-sessions {
          type string;
        }

        // system / login-control / ssh outbound-max-sessions
        leaf outbound-max-sessions {
          type string;
        }

        // system / login-control / ssh ttl-security
        leaf ttl-security {
          type string;
        }
      }

      // system / login-control / telnet
      container telnet {
        tailf:cli-add-mode;

        // system / login-control / telnet enable-graceful-shutdown
        leaf enable-graceful-shutdown {
          type empty;
        }

        // system / login-control / telnet inbound-max-sessions
        leaf inbound-max-sessions {
          type string;
        }

        // system / login-control / telnet / outbound-max-sessions
        leaf outbound-max-sessions {
          type string;
        }

        // system / login-control / telnet / ttl-security
        leaf ttl-security {
          type string;
        }
      }
    }

    // system / lsr-load-balancing
    container lsr-load-balancing {
      choice choice {

        // system / lsr-load-balancing lbl-only
        leaf lbl-only {
          type empty;
        }

        // system / lsr-load-balancing lbl-ip
        leaf lbl-ip {
          type empty;
        }

        // system / lsr-load-balancing ip-only
        leaf ip-only {
          type empty;
        }
      }
    }

    // system / mc-enh-load-balancing
    leaf mc-enh-load-balancing {
      type empty;
    }

    // system / mixed-mode
    leaf mixed-mode {
      type empty;
    }

    // system / name
    leaf name {
      type string;
    }

    // system / netconf
    container netconf {
      tailf:cli-add-mode;

      // system / netconf shutdown
      leaf shutdown {
        tailf:cli-boolean-no;
        default true;
        type boolean;
      }
    }

    // system / persistence /
    container persistence {
      tailf:cli-add-mode;

      // system / persistence / ancp
      container ancp {

        // system / persistence / ancp description
        leaf description {
          tailf:cli-embed-no-on-delete;
          tailf:cli-no-value-on-delete;
          type string;
        }

        // system / persistence / location
        leaf location {
          type string;
        }
      }

      // system / persistence / application-assurance /
      container application-assurance {
        tailf:cli-add-mode;

        // system / persistence / application-assurance /  description
        leaf description {
          tailf:cli-embed-no-on-delete;
          tailf:cli-no-value-on-delete;
          type string;
        }

        // system / persistence / application-assurance / location
        leaf location {
          type string;
        }
      }

      // system / persistence / dhcp-server /
      container dhcp-server {
        tailf:cli-add-mode;

        // system / persistence / dhcp-server /  description
        leaf description {
          tailf:cli-embed-no-on-delete;
          tailf:cli-no-value-on-delete;
          type string;
        }

        // system / persistence / dhcp-server / location
        leaf location {
          type string;
        }
      }

      // system / persistence / nat-port-forwarding /
      container nat-port-forwarding {
        tailf:cli-add-mode;

        // system / persistence / nat-port-forwarding / description
        leaf description {
          tailf:cli-embed-no-on-delete;
          tailf:cli-no-value-on-delete;
          type string;
        }

        // system / persistence / nat-port-forwarding / location
        leaf location {
          type string;
        }
      }

      // system / persistence / subscriber-mgmt /
      container subscriber-mgmt {
        tailf:cli-add-mode;

        // system / persistence / subscriber-mgmt / description
        leaf description {
          tailf:cli-embed-no-on-delete;
          tailf:cli-no-value-on-delete;
          type string;
        }

        // system / persistence / subscriber-mgmt / location
        leaf location {
          type string;
        }
      }
    }

    // system / persistence / snmp /
    container snmp {
      tailf:cli-add-mode;
      tailf:cli-embed-no-on-delete;

      // system / persistence / snmp / engineID
      leaf engineID {
        type string;
      }

      // system / persistence / snmp / general-port
      leaf general-port {
        type uint16;
      }

      // system / persistence / snmp / packet-size
      leaf packet-size {
        type uint16;
      }

      // system / persistence / snmp / shutdown
      leaf shutdown {
        tailf:cli-boolean-no;
        default true;
        type boolean;
      }
    }

    // system / rollback /
    container rollback {
      tailf:info "Configure general rollback parameters";
      tailf:cli-add-mode;

      // system / rollback / local-max-checkpoints
      leaf local-max-checkpoints {
         tailf:info "Configures the maximum rollback files on compact flash";
         tailf:cli-no-value-on-delete;
        type uint8 {
          range "1..50";
        }
      }

      // system / rollback / remote-max-checkpoints
       leaf remote-max-checkpoints {
         tailf:info "Configures the maximum rollback files saved "
                 + "at a remote location (ftp)";
         tailf:cli-no-value-on-delete;
        type uint8 {
          range "1..200";
        }
      }

      // system / rollback / rescue-location
       leaf rescue-location {
         tailf:info "Configures the location of the rollback rescue file";
         type string;
       }

      // system / rollback / rollback-location
       leaf rollback-location {
         tailf:info "Configures the location and filename of the rollback "
                 +"checkpoint files";
         type string;
       }
     }

    // system /  time /
    container time {
      tailf:cli-add-mode;

      // system /  time / ntp /
      container ntp {
        tailf:cli-add-mode;

        // system / time / ntp / authentication-check
        leaf authentication-check {
          tailf:info "Configure the option to skip the rejection of NTP PDUs";
          type empty;
         }

        // system / time / ntp / authentication-key *
        list authentication-key {
          tailf:info "Configure the authentication key and type used "+
                    "to verify NTP PDUs";
          tailf:cli-embed-no-on-delete;
          tailf:cli-suppress-mode;
          tailf:cli-compact-syntax;
          tailf:cli-sequence-commands;
          key key-id;
          leaf key-id {
            type uint8 {
              range "1..255";
            }
          }

          // system / time / ntp / authentication-key * key
          leaf key {
            tailf:cli-no-name-on-delete;
            tailf:cli-no-value-on-delete;
            type string {
              length "1..32";
            }
          }

          // system / time / ntp / authentication-key * hash
          leaf hash {
            tailf:cli-drop-node-name;
            tailf:cli-no-value-on-delete;
            type enumeration {
              enum hash;
              enum hash2;
            }
          }

          // system / time / ntp / authentication-key * type
          leaf type {
            tailf:cli-no-name-on-delete;
            tailf:cli-no-value-on-delete;
            type enumeration {
              enum des;
              enum message-digest;
            }
          }
        }

        // system /  time / ntp / server *
        list server {
          tailf:info "Configure NTP to use the specified address"
            +" as an NTP server";
          tailf:cli-embed-no-on-delete;
          tailf:cli-suppress-mode;
          key address;

          leaf address {
            type union {
              type inet:ipv4-address;
              type inet:ipv6-address;
            }
          }

          // system /  time / ntp / server * key-id
          leaf key-id {
            tailf:cli-no-name-on-delete;
            tailf:cli-no-value-on-delete;
            type uint8;
          }

          // system /  time / ntp / server * version
          leaf version {
            tailf:cli-no-name-on-delete;
            tailf:cli-no-value-on-delete;
            type uint8 {
              range "1..4";
            }
          }

          // system /  time / ntp / server * prefer
          leaf prefer {
            tailf:cli-no-name-on-delete;
            type empty;
          }
        }

        // system /  time / ntp / shutdown
        leaf shutdown {
          tailf:cli-boolean-no;
          default true;
          type boolean;
        }
      }

      // system /  time / sntp /
      container sntp {
        tailf:cli-add-mode;

        // system /  time / sntp / broadcast-client
        leaf broadcast-client {
          type empty;
        }

        // system /  time / sntp / server-address
        container server-address {
          tailf:cli-compact-syntax;
          tailf:cli-sequence-commands;

          // system /  time / sntp / server-address +
          // broadcast-client ip
          leaf ip {
            tailf:cli-drop-node-name;
            type inet:ipv4-address;
          }

          // system /  time / sntp / server-address +
          // broadcast-client version
          leaf version {
            tailf:cli-drop-node-name;
            tailf:cli-optional-in-sequence;
            type uint8 {
              range "1..3";
            }
          }

          // system /  time / sntp / server-address +
          // broadcast-client mode
          leaf mode {
            tailf:cli-drop-node-name;
            type enumeration {
              enum normal;
              enum preferred;
            }
          }

          // system /  time / sntp / server-address +
          // broadcast-client interval
          leaf interval {
            type uint32;
          }
        }

        // system /  time / sntp / shutdown
        leaf shutdown {
          tailf:cli-boolean-no;
          default true;
          type boolean;
        }
      }

      // system /  time / zone
      container zone {
        tailf:cli-compact-syntax;
        tailf:cli-sequence-commands;

        // system /  time / zone name
        leaf name {
          tailf:cli-drop-node-name;
          type string;
        }

        // system /  time / zone time
        leaf time {
          tailf:cli-drop-node-name;
          type string;
        }
      }

      // system /  time / dst-zone
      container dst-zone {
        tailf:cli-add-mode;

        // system /  time / dst-zone name
        leaf name {
          tailf:cli-drop-node-name;
          tailf:cli-hide-in-submode;
          type string;
        }

        // system /  time / dst-zone / start
        container start {
          tailf:cli-sequence-commands;
          tailf:cli-compact-syntax;
          tailf:cli-no-name-on-delete;
          uses time-stamp;
        }

        // system /  time / dst-zone / end
        container end {
          tailf:cli-sequence-commands;
          tailf:cli-compact-syntax;
          tailf:cli-no-name-on-delete;
          uses time-stamp;
        }
      }
    }

    // system /  thresholds /
    container thresholds {
      tailf:cli-add-mode;

      // system /  thresholds / rmon /
      container rmon {
        tailf:cli-add-mode;

        // system /  thresholds / rmon / alarm
        leaf alarm {
          type empty;
        }

        // system /  thresholds / rmon / event
        leaf event {
          type empty;
        }
      }
    }

    // system /  power-supply *
    list power-supply {
      tailf:cli-embed-no-on-delete;
      tailf:cli-suppress-mode;
      key power-supply-id;
      leaf power-supply-id {
        type string;
      }
    }


    // system / security
    container security {
      tailf:info "Configure system security related parameters";
      tailf:cli-add-mode;

      // system / security / hash-control
      container hash-control {
        tailf:info "Configure system security hash-control";

        // system / security / hash-control / read-version
        leaf read-version {
          type enumeration {
            enum 1;
            enum 2;
            enum all;
          }
        }

        // system / security / hash-control / write-version
        leaf write-version {
          type enumeration {
            enum 1;
            enum 2;
          }
        }
      }

      // system / security / profile
      list profile {
        tailf:info "Create/delete user profiles";
        tailf:cli-embed-no-on-delete;
        key name;
        leaf name {
          type string;
        }

        // system / security / profile / default-action
        leaf default-action {
          tailf:info "Default action for the profile";
          tailf:cli-no-value-on-delete;
          type enumeration {
            enum deny-all;
            enum permit-all;
            enum none;
          }
        }
        // system / security / profile / entry *
        list entry {
          tailf:info "Match criteria entry for the profile";
          key entry-id;
          // system / security / profile / entry * / entry-id
          leaf entry-id {
            type uint16 {
              range "1..9999";
            }
          }
          // system / security / profile / entry * / action
          leaf action {
            tailf:info "Action to take when a user command matches this entry";
            type enumeration {
              enum permit;
              enum deny;
            }
          }
          // system / security / profile / entry * / description
          leaf description {
            tailf:info "Description for this entry";
            type string {
              length "1..80";
            }
          }
          // system / security / profile / entry * / match
          leaf match {
            tailf:info "Description for this entry";
            type string {
              length "1..256";
            }
          }
        }
      }

      // system / security / password
      container password {
        tailf:info "Configure password related parameters";
        tailf:cli-add-mode;

        // system / security / password / health-check
        leaf health-check {
          tailf:info "Enable/disable dynamic monitoring of radius and tacplus";
          tailf:cli-no-value-on-delete;
          type uint16 {
            range "6..1500";
          }
        }

        leaf-list authentication-order {
          tailf:info "Sequence in which user password is authenticated";
          tailf:cli-flat-list-syntax;
          type enumeration {
            enum "local";
            enum "radius";
            enum "tacplus";
          }
        }

        container attempts {
          tailf:info "Max number of unsuccessful login attempts allowed "
                    +"in a specified time frame";
          tailf:cli-compact-syntax;
          tailf:cli-sequence-commands {
            tailf:cli-reset-all-siblings;
          }
          leaf count {
            tailf:cli-drop-node-name;
            tailf:cli-no-value-on-delete;
            type uint8;
          }
          leaf time {
            tailf:cli-break-sequence-commands;
            tailf:cli-no-value-on-delete;
            tailf:cli-no-name-on-delete;
            type uint8;
          }
          leaf lockout {
            tailf:cli-no-value-on-delete;
            tailf:cli-no-name-on-delete;
            type uint8;
          }
        }
      }

      // system / security / radius
      container radius {
        tailf:info "Configure RADIUS authentication parameters";
        tailf:cli-add-mode;

        // system / security / radius / authorization
        leaf authorization {
          tailf:info "Enable/disable RADIUS command accounting";
          type empty;
        }

        // system / security / radius / accounting
        leaf accounting {
          tailf:info "Enable/disable RADIUS command authorization";
          type empty;
        }

        // system / security / radius / server *
        list server {
          tailf:info "Add/remove a RADIUS server";
          tailf:cli-embed-no-on-delete;
          tailf:cli-suppress-mode;
          tailf:cli-compact-syntax;
          key server-index;
          leaf server-index {
            tailf:cli-drop-node-name;
            tailf:cli-no-value-on-delete;
            type uint32;
          }

          // system / security / radius / server * / address
          leaf address {
            tailf:cli-no-value-on-delete;
            mandatory true;
            type inet:ipv4-address;
          }

          // system / security / radius / server * / secret
          leaf secret {
            tailf:cli-no-value-on-delete;
            mandatory true;
            type string;
          }

          // system / security / radius / server * / hash
          leaf type {
            tailf:cli-drop-node-name;
            tailf:cli-no-value-on-delete;
            mandatory true;
            type enumeration {
              enum "hash";
              enum "hash2";
            }
          }
        }
      }


      // system / security / tacplus
      container tacplus {
        tailf:info "Configure TACACS+ authentication parameters for"
                  +" the system";
        tailf:cli-embed-no-on-delete;
        tailf:cli-add-mode;
        // system / security / tacplus / accounting
        container accounting {
          tailf:info "Enable/disable TACACS+ command accounting";
          tailf:cli-embed-no-on-delete;
          // system / security / tacplus / accounting / record-type
          leaf record-type {
            tailf:cli-no-name-on-delete;
            tailf:cli-no-value-on-delete;
            type enumeration {
              enum start-stop;
              enum stop-only;
            }
          }
        }
        // system / security / tacplus / authorization
        container authorization {
          tailf:info "Enable/disable TACACS+ command authorization";
          tailf:cli-embed-no-on-delete;
          presence true;
          // system / security / tacplus / authorization / use-prix-lvl
          leaf use-prix-lvl {
            tailf:cli-no-name-on-delete;
            type empty;
          }
        }
        // system / security / tacplus / interactive-authentication
        leaf interactive-authentication {
          tailf:info "Enable/disable TACACS+ interactive authentication";
          type empty;
        }
        // system / security / tacplus / priv-lvl-map
        container priv-lvl-map {
          tailf:info "Configure privilege level mapping";
          tailf:cli-embed-no-on-delete;
          tailf:cli-add-mode;
          // system / security / tacplus / priv-lvl-map / priv-lvl *
          list priv-lvl {
            tailf:info "Configure a user profile for this privilege level";
            tailf:cli-suppress-mode;
            key lvl;
            leaf lvl {
              type uint8 {
                range "0..15";
              }
            }
            // system / security / tacplus / priv-lvl-map / priv-lvl *
            // user-profile
            leaf user-profile {
              tailf:cli-drop-node-name;
              tailf:cli-no-value-on-delete;
              type union {
                type enumeration {
                  enum "default";
                }
                type string;
              }
            }
          }
        }
        // system / security / tacplus / server *
        list server {
          tailf:info "Add/remove a TACACS+ server";
          tailf:cli-suppress-mode;
          tailf:cli-compact-syntax;
          key server-index;
          leaf server-index {
            type uint8 {
              range "1..5";
            }
          }
          // system / security / tacplus / server * address
          leaf address {
            tailf:cli-no-value-on-delete;
            tailf:cli-no-name-on-delete;
            type union {
              type inet:ipv4-address;
              type inet:ipv6-address;
            }
          }
          // system / security / tacplus / server * secret
          leaf secret {
            tailf:cli-no-value-on-delete;
            tailf:cli-no-name-on-delete;
            type string {
              length "1..255";
            }
          }
          // system / security / tacplus / server * hash
          leaf hash {
            tailf:cli-drop-node-name;
            tailf:cli-no-value-on-delete;
            default hash2;
            type enumeration {
              enum hash;
              enum hash2;
            }
          }
          // system / security / tacplus / server * port
          leaf port {
            tailf:cli-no-value-on-delete;
            tailf:cli-no-name-on-delete;
            type uint16;
          }
        }
        // system / security / tacplus / timeout
        leaf timeout {
          tailf:info "Timeout for a response from the TACACS+ server";
          tailf:cli-no-value-on-delete;
          type uint32;
        }
        // system / security / tacplus / use-default-template
        leaf use-default-template {
          tailf:info "Enable/disable TACACS+ default template";
          type empty;
        }
        // system / security / tacplus / shutdown
        leaf shutdown {
          tailf:info "Enable/disable TACACS+ protocol operation";
          tailf:cli-boolean-no;
          default true;
          type boolean;
        }
      }
      // system / security / telnet-server
      leaf telnet-server {
        tailf:info "Start/Stop telnet server";
        type empty;
      }

       // system / security / telnet-server
      leaf telnet6-server {
        tailf:info "Start/Stop telnet IPv6 server";
        type empty;
      }

      // system / security / ftp-server
      leaf ftp-server {
        tailf:info "Start/Stop FTP server";
        type empty;
      }

      // system / security / per-peer-queuing
      leaf per-peer-queuing {
        tailf:info "Enable/disable CPM hardware queuing per peer";
        type empty;
      }

      // system / security / snmp
      container snmp {
        tailf:info "Configure SNMP security parameters";
        tailf:cli-add-mode;

        // system / security / snmp / access
        container access {
          tailf:info "Configure access groups for SNMP security";
          tailf:cli-embed-no-on-delete;

          // system / security / snmp / access group *
          list group {
            tailf:info "Group name";
            tailf:cli-suppress-mode;
            tailf:cli-compact-syntax;
            tailf:cli-sequence-commands;
            key name;
            leaf name {
              type string;
            }

            // system / security / snmp / access group * security-model
            leaf security-model {
              type enumeration {
                enum usm;
                enum snmpv1;
                enum snmpv2c;
                enum snmpv2ac;
              }
            }

            // system / security / snmp / access group * security-level
            leaf security-level {
              type enumeration {
                enum auth-no-privacy;
              }
            }

            // system / security / snmp / access group * read
            leaf read {
              type string;
            }

            // system / security / snmp / access group * notify
            leaf notify {
              type string;
            }
          }
        }

        // system / security / snmp / community *
        list community {
          tailf:info "Create/delete SNMP community strings";
          tailf:cli-suppress-mode;
          tailf:cli-compact-syntax;
          tailf:cli-sequence-commands;
          tailf:cli-embed-no-on-delete;
          key name;
          leaf name {
            type string;
          }

          // system / security / snmp / community * type
          leaf type {
            tailf:cli-drop-node-name;
            tailf:cli-no-value-on-delete;
            tailf:cli-optional-in-sequence;
            default hash2;
            type enumeration {
              enum hash;
              enum hash2;
            }
          }
          // system / security / snmp / community * access-parameters
          leaf access-parameters {
            tailf:cli-drop-node-name;
            tailf:cli-no-value-on-delete;
            type enumeration {
              enum r;
              enum rw;
              enum rwa;
              enum mgmt;
              enum vpls-mgmt;
            }
          }

          // system / security / snmp / community * version
          leaf version {
            tailf:cli-no-name-on-delete;
            tailf:cli-no-value-on-delete;
            tailf:cli-optional-in-sequence;
            type enumeration {
              enum v2c;
              enum v1;
              enum both;
            }
          }
          // system / security / snmp / community * src-access-list
          leaf src-access-list {
            tailf:cli-no-name-on-delete;
            tailf:cli-no-value-on-delete;
            tailf:cli-optional-in-sequence;
            type string;
          }
        }
      }

      // system / security / source-address
      container source-address {
        tailf:info "Configure source address for various applications";
        tailf:cli-add-mode;
        // system / security / source-address / application *
        list application {
          tailf:info "Configure application to use source address";
          tailf:cli-embed-no-on-delete;
          tailf:cli-suppress-mode;
          key name;
          leaf name {
            type string;
          }
          // system / security / source-address / application * address
          leaf address {
            tailf:cli-drop-node-name;
            tailf:cli-no-value-on-delete;
            type union {
              type string;
              type inet:ipv4-address;
            }
          }
        }
      }

      // system / security / ssh
      container ssh {
        tailf:info "Configure SSH parameters";
        tailf:cli-add-mode;

        // system / security / ssh / preserve-key
        leaf preserve-key {
          tailf:info "enable/disable persistence of host-key";
          type empty;
        }

        // system / security / ssh / server-shutdown
        leaf server-shutdown {
          tailf:info "start/stop SSH server";
          type empty;
        }

         // system / security / ssh / version
         leaf version {
           tailf:info "Configure the SSH version";
           tailf:cli-no-value-on-delete;
           type enumeration {
             enum "1";
             enum "2";
             enum "1-2";
           }
        }
      }

      // system / security / user
      list user {
        tailf:info " Configure a local user";
        tailf:cli-embed-no-on-delete;
        key user-id;
        leaf user-id {
          type string;
        }

        // system / security / user * / access
          leaf-list access {
            tailf:info "Grant/deny a user access permissions "
                      + "for ftp snmp netconf or console";
            tailf:cli-flat-list-syntax;
            type enumeration {
              enum "console";
              enum "snmp";
              enum "ftp";
              enum "li";
              enum "netconf";
            }
          }


        // system / security / user * / console
        container console {
          tailf:info "Configure user profile membership for the console";
          tailf:cli-add-mode;

          // system / security / user * / console / cannot-change-password
          leaf cannot-change-password {
            tailf:info "Allow/disallow password changing privileges";
            type empty;
          }

          // system / security / user * / console / login-exec
          leaf login-exec {
            tailf:info "File to be executed when a user successfully logs in";
            tailf:cli-no-value-on-delete;
            type string;
          }

          // system / security / user * / console / member
          list member {
            tailf:info " Allow user to access a profile";
            tailf:cli-suppress-mode;
            key name;
            leaf name {
              type string;
            }
          }

          // system / security / user * / console / new-password-at-login
          leaf new-password-at-login {
            tailf:info "Enable/disable prompting a user to change "
                      +"password at login";
            type empty;
          }
        }

        // system / security / user * / home-directory
        leaf home-directory {
          tailf:info "Home directory for the user";
          tailf:cli-no-value-on-delete;
          type string;
        }

        // system / security / user * / password
        container password {
          tailf:info "Password for the user";
          tailf:cli-compact-syntax;
          tailf:cli-sequence-commands;
          tailf:cli-embed-no-on-delete;

          leaf id {
            tailf:cli-drop-node-name;
            tailf:cli-no-value-on-delete;
            type string;
          }

          leaf method {
            tailf:cli-drop-node-name;
            tailf:cli-no-value-on-delete;
            type enumeration {
              enum hash2;
            }
          }
        }

        // system / security / user * / restricted-to-home
        leaf restricted-to-home {
          tailf:info "Restrict user to home directory";
          type empty;
        }

        // system / security / user * / snmp
        container snmp {
          tailf:info "Configure SNMP group membership for the user";
          tailf:cli-add-mode;

          // system / security / user * / snmp / authentication
          container authentication {
            tailf:info "Authentication in the SNMP model";
            tailf:cli-compact-syntax;
            tailf:cli-sequence-commands;
            tailf:cli-embed-no-on-delete;

            // system / security / user * / snmp / authentication / hash
            leaf hash {
              tailf:cli-no-value-on-delete;
              tailf:cli-no-name-on-delete;
              type enumeration {
                enum md5;
                enum sha;
              }
            }

            // system / security / user * / snmp / authentication / key-1
            leaf key-1 {
              tailf:cli-drop-node-name;
              tailf:cli-no-value-on-delete;
              type string;
            }

            // system / security / user * / snmp / authentication / privacy
            leaf privacy {
              tailf:cli-no-value-on-delete;
              tailf:cli-no-name-on-delete;
              type enumeration {
                enum none;
                enum des-key;
                enum aes-128-cfb-key;
              }
            }

            // system / security / user * / snmp / authentication / key-2
            leaf key-2 {
              tailf:cli-drop-node-name;
              tailf:cli-no-value-on-delete;
              //when "not ../privacy=none";
              type string;
            }

            // system / security / user * / snmp / authentication / hashval
            leaf hashval {
              tailf:cli-drop-node-name;
              tailf:cli-no-value-on-delete;
              type string;
            }
          }

          // system / security user * / snmp / group
          leaf group {
            tailf:info "Associate the user with a group name";
            tailf:cli-no-value-on-delete;
            type string;
          }
        }
      }

      // system / security / cpu-protection
      container cpu-protection {
        tailf:info "Configure CPU protection";
        tailf:cli-add-mode;

        // system / security / cpu-protection / link-specific-rate
        leaf link-specific-rate {
          tailf:info "Configure a link-specific rate for CPU protection";
          tailf:cli-no-value-on-delete;
          type uint32;
        }

        // system / security / cpu-protection / policy *
        list policy {
          tailf:info "Configure a CPU protection policy";
          tailf:cli-embed-no-on-delete;
          key policy-id;
          leaf policy-id {
            type uint16;
          }

          // system / security / cpu-protection / policy * / create
          leaf create {
            tailf:cli-hide-in-submode;
            tailf:cli-no-name-on-delete;
            mandatory true;
            type empty;
          }

          // system / security / cpu-protection / policy * / overall-rate
          leaf overall-rate {
            tailf:info "Configure an overall packet arrival rate limit";
            type union {
              type enumeration {
                enum max;
              }
              type uint32 {
                range "1..100000000";
              }
            }
          }
        }

        // system / security / cpu-protection / protocol-protection
        leaf protocol-protection {
          tailf:info "Enable/Disable DOS protection of network "
                    +"control protocols";
          type empty;
        }

        // system / security / cpu-protection / port-overall-rate
        leaf port-overall-rate {
          tailf:info "Configure a per-port overall rate limit for CPU protect";
          type union {
            type enumeration {
              enum max;
            }
            type uint32 {
              range "1..100000000";
            }
          }
        }
      }

      // system / security / cpm-filter
      container cpm-filter {
        tailf:info "Configure a CPM filter";
        tailf:cli-add-mode;

        // system / security / cpm-filter / default-action
        leaf default-action {
          tailf:info "Configure the default filter action";
          type enumeration {
            enum "accept";
            enum "drop";
          }
        }

        // system / security / cpm-filter / ip-filter /
        container ip-filter {
          tailf:info "Configure a CPM IP-filter";
          tailf:cli-add-mode;

          // system / security / cpm-filter / ip-filter / entry *
          list entry {
            tailf:info "Configure ip-filter entry";
            tailf:cli-embed-no-on-delete;
            key entry-id;
            leaf entry-id {
              type uint16;
            }

            // system / security / cpm-filter / ip-filter / entry * / create
            leaf create {
              mandatory true;
              type empty;
              tailf:cli-hide-in-submode;
              tailf:cli-no-name-on-delete;
            }

            // system / security / cpm-filter / ip-filter /
            // entry * / action
            container action {
              tailf:info "Configure action for the filter entry";
              tailf:cli-compact-syntax;
              tailf:cli-embed-no-on-delete;
              choice action-choice {
                leaf drop {
                  tailf:cli-no-name-on-delete;
                  type empty;
                }

                leaf accept {
                  tailf:cli-no-name-on-delete;
                  type empty;
                }

                leaf queue {
                  tailf:cli-no-name-on-delete;
                  tailf:cli-no-value-on-delete;
                  type uint16 {
                    range "33..2000";
                  }
                }
              }
            }

            // system / security / cpm-filter / ip-filter /
            // entry * / description
            leaf description {
              tailf:info "Description for this filter entry";
              tailf:cli-no-value-on-delete;
              type string {
                length "1..80";
              }
            }

            // system / security / cpm-filter / ip-filter /
            // entry * / log
            leaf log {
              tailf:info "Configure log for the filter entry";
              tailf:cli-no-value-on-delete;
              type uint16;
            }

            // system / security / cpm-filter / ip-filter /
            // entry * / match /
            container match {
              tailf:info "Configure match criteria for this ip filter entry";
              tailf:cli-add-mode;
              tailf:cli-embed-no-on-delete;

              // system / security / cpm-filter / ip-filter /
              // entry * / match / protocol
              leaf protocol {
                tailf:cli-hide-in-submode;
                tailf:cli-no-name-on-delete;
                tailf:cli-no-value-on-delete;
                type protocol;
              }

              // system / security / cpm-filter / ip-filter /
              // entry * / match / dscp
              leaf dscp {
                tailf:info "Configure DSCP match condition";
                tailf:cli-no-value-on-delete;
                type dscp-type;
              }

              // system / security / cpm-filter / ip-filter /
              // entry * / match / dst-ip
              container dst-ip {
                tailf:info "Configure dest. ip match condition";
                tailf:cli-embed-no-on-delete;
                tailf:cli-compact-syntax;
                tailf:cli-sequence-commands;
                uses filter-match-ip-grouping;
              }

              // system / security / cpm-filter / ip-filter /
              // entry * / match / dst-port
              container dst-port {
                tailf:info "Configure dest. port match condition";
                tailf:cli-embed-no-on-delete;
                tailf:cli-compact-syntax;
                tailf:cli-sequence-commands;
                uses cpm-filter-match-port-grouping;
              }

              // system / security / cpm-filter / ip-filter /
              // entry * / match / fragment
              leaf fragment {
                tailf:info "Configure fragmentation match condition";
                tailf:cli-no-value-on-delete;
                type boolean;
              }

              // system / security / cpm-filter / ip-filter /
              // entry * / match / icmp-code
              leaf icmp-code {
                tailf:info "Configure ICMP code match condition";
                tailf:cli-no-value-on-delete;
                type uint32;
              }

              // system / security / cpm-filter / ip-filter /
              // entry * / match / icmp-type
              leaf icmp-type {
                tailf:info "Configure ICMP type match condition";
                tailf:cli-no-value-on-delete;
                type icmp-type;
              }

              // system / security / cpm-filter / ip-filter /
              // entry * / match / ip-option
              container ip-option {
                tailf:info "Configure ip-option match condition";
                tailf:cli-embed-no-on-delete;
                tailf:cli-compact-syntax;

                leaf value {
                  tailf:cli-drop-node-name;
                  tailf:cli-no-value-on-delete;
                  type uint8;
                }

                leaf mask {
                  tailf:cli-drop-node-name;
                  tailf:cli-no-value-on-delete;
                  type uint8;
                }
              }

              // system / security / cpm-filter / ip-filter /
              // entry * / match / multiple-option
              leaf multiple-option {
                tailf:info "Configure multiple-option match condition";
                tailf:cli-no-value-on-delete;
                type boolean;
              }

              // system / security / cpm-filter / ip-filter /
              // entry * / match / option-present
              leaf option-present {
                tailf:info "Configure option-present match condition";
                tailf:cli-no-value-on-delete;
                type boolean;
              }

              // system / security / cpm-filter / ip-filter /
              // entry * / match / port
              container port {
                tailf:info "Configure port match condition";
                tailf:cli-embed-no-on-delete;
                tailf:cli-compact-syntax;
                tailf:cli-sequence-commands;
                uses cpm-filter-match-port-grouping;
              }

              // system / security / cpm-filter / ip-filter /
              // entry * / match / router
              leaf router {
                tailf:info "Match a router|service-id";
                tailf:cli-no-value-on-delete;
                type union {
                  type string {
                    length "1..32";
                  }
                  type uint32 {
                    range "1..2147483647";
                  }
                }
              }

              // system / security / cpm-filter / ip-filter /
              // entry * / match / src-ip
              container src-ip {
                tailf:info "Configure source ip match condition";
                tailf:cli-embed-no-on-delete;
                tailf:cli-compact-syntax;
                tailf:cli-sequence-commands;
                uses filter-match-ip-grouping;
              }

              // system / security / cpm-filter / ip-filter /
              // entry * / match / src-port
              container src-port {
                tailf:info "Configure source port match condition";
                tailf:cli-embed-no-on-delete;
                tailf:cli-compact-syntax;
                tailf:cli-sequence-commands;
                uses cpm-filter-match-port-grouping;
              }

              // system / security / cpm-filter / ip-filter /
              // entry * / match / tcp-ack
              leaf tcp-ack {
                tailf:info "Configure TCP ACK match condition";
                tailf:cli-no-value-on-delete;
                type boolean;
              }

              // system / security / cpm-filter / ip-filter /
              // entry * / match / tcp-syn
              leaf tcp-syn {
                tailf:info " Configure TCP SYN match condition";
                tailf:cli-no-value-on-delete;
                type boolean;
              }
            }
          }

          // system / security / cpm-filter / ip-filter / shutdown
          leaf shutdown {
            tailf:info "Set the admin state of the IP filter";
            tailf:cli-boolean-no;
            default true;
            type boolean;
          }
        }

        // system / security / cpm-filter / ipv6-filter /
        container ipv6-filter {
          tailf:info "Configure a CPM IPv6-filter";
          tailf:cli-add-mode;

          // system / security / cpm-filter / ipv6-filter / entry *
          list entry {
            tailf:info "Configure IPv6-filter entry";
            tailf:cli-embed-no-on-delete;
            key entry-id;
            leaf entry-id {
              type uint16;
            }

            // system / security / cpm-filter / ipv6-filter /
            // entry * / create
            leaf create {
              mandatory true;
              type empty;
              tailf:cli-hide-in-submode;
              tailf:cli-no-name-on-delete;
            }

            // system / security / cpm-filter / ipv6-filter /
            // entry * / action
            container action {
              tailf:info "Configure action for the IPv6-filter entry";
              tailf:cli-compact-syntax;
              tailf:cli-embed-no-on-delete;
              choice action-choice {
                leaf drop {
                  tailf:cli-no-name-on-delete;
                  type empty;
                }

                leaf accept {
                  tailf:cli-no-name-on-delete;
                  type empty;
                }

                leaf queue {
                  tailf:cli-no-name-on-delete;
                  tailf:cli-no-value-on-delete;
                  type uint16 {
                    range "33..2000";
                  }
                }
              }
            }

            // system / security / cpm-filter / ipv6-filter /
            // entry * / description
            leaf description {
              tailf:info "Description for this filter entry";
              tailf:cli-no-value-on-delete;
              type string {
                length "1..80";
              }
            }

            // system / security / cpm-filter / ipv6-filter /
            // entry * / log
            leaf log {
              tailf:info "Configure log for the IPv6-filter entry";
              tailf:cli-no-value-on-delete;
              type uint16;
            }

            // system / security / cpm-filter / ipv6-filter /
            // entry * / match /
            container match {
              tailf:info "Configure match criteria for this IPv6 filter entry";
              tailf:cli-add-mode;
              tailf:cli-embed-no-on-delete;

              // system / security / cpm-filter / ipv6-filter /
              // entry * / match / protocol
              leaf next-header {
                tailf:cli-hide-in-submode;
                tailf:cli-no-name-on-delete;
                tailf:cli-no-value-on-delete;
                type protocol;
              }

              // system / security / cpm-filter / ipv6-filter /
              // entry * / match / dscp
              leaf dscp {
                tailf:info "Configure DSCP match condition";
                tailf:cli-no-value-on-delete;
                type dscp-type;
              }

              // system / security / cpm-filter / ipv6-filter /
              // entry * / match / dst-ip
              leaf dst-ip {
                tailf:info "Configure dest. IPv6 addr  match condition";
                tailf:cli-no-value-on-delete;
                type union {
                  type tailf:ipv6-address-and-prefix-length;
                  type string;
                }
              }

              // system / security / cpm-filter / ipv6-filter /
              // entry * / match / dst-port
              container dst-port {
                tailf:info "Configure dest. port match condition";
                tailf:cli-embed-no-on-delete;
                tailf:cli-compact-syntax;
                tailf:cli-sequence-commands;
                uses cpm-filter-match-port-grouping;
              }

              // system / security / cpm-filter / ipv6-filter /
              // entry * / match / flow-label
              leaf flow-label {
                tailf:info "Configure flow label match condition";
                tailf:cli-no-value-on-delete;
                type uint32 {
                  range "0..1048575";
                }
              }

              // system / security / cpm-filter / ipv6-filter /
              // entry * / match / hop-by-hop-opt
              leaf hop-by-hop-opt {
                tailf:info "Configure hop by hop match condition";
                tailf:cli-no-value-on-delete;
                type boolean;
              }

              // system / security / cpm-filter / ipv6-filter /
              // entry * / match / icmp-code
              leaf icmp-code {
                tailf:info "Configure ICMP code match condition";
                tailf:cli-no-value-on-delete;
                type uint32;
              }

              // system / security / cpm-filter / ipv6-filter /
              // entry * / match / icmp-type
              leaf icmp-type {
                tailf:info "Configure ICMP type match condition";
                tailf:cli-no-value-on-delete;
                type icmpv6-type;
              }

              // system / security / cpm-filter / ipv6-filter /
              // entry * / match / port
              container port {
                tailf:info "Configure port match condition";
                tailf:cli-embed-no-on-delete;
                tailf:cli-compact-syntax;
                tailf:cli-sequence-commands;
                uses cpm-filter-match-port-grouping;
              }

              // system / security / cpm-filter / ipv6-filter /
              // entry * / match / router
              leaf router {
                tailf:info "Match a router|service-id";
                tailf:cli-no-value-on-delete;
                type union {
                  type string {
                    length "1..32";
                  }
                  type uint32 {
                    range "1..2147483647";
                  }
                }
              }

              // system / security / cpm-filter / ipv6-filter /
              // entry * / match / src-ip
              container src-ip {
                tailf:info "Configure source IPv6 address match condition";
                tailf:cli-embed-no-on-delete;
                tailf:cli-compact-syntax;
                tailf:cli-sequence-commands;
                uses filter-match-ipv6-grouping;
              }

              // system / security / cpm-filter / ipv6-filter /
              // entry * / match / src-port
              container src-port {
                tailf:info "Configure source port match condition";
                tailf:cli-embed-no-on-delete;
                tailf:cli-compact-syntax;
                tailf:cli-sequence-commands;
                uses cpm-filter-match-port-grouping;
              }

              // system / security / cpm-filter / ipv6-filter /
              // entry * / match / tcp-ack
              leaf tcp-ack {
                tailf:info "Configure TCP ACK match condition";
                tailf:cli-no-value-on-delete;
                type boolean;
              }

              // system / security / cpm-filter / ipv6-filter /
              // entry * / match / tcp-syn
              leaf tcp-syn {
                tailf:info "Configure TCP SYN match condition";
                tailf:cli-no-value-on-delete;
                type boolean;
              }
            }
          }

          // system / security / cpm-filter / ipv6-filter / shutdown
          leaf shutdown {
            tailf:info "Set the admin state of the IPv6 filter";
            tailf:cli-boolean-no;
            default false;
            type boolean;
          }
        }
      }

      // system / security / cpm-queue
      container cpm-queue {
        tailf:info "Configure a CPM queue";
        tailf:cli-add-mode;

        // system / security / cpm-queue / queue
        list queue {
          tailf:info "Configure a Queue";
          tailf:cli-embed-no-on-delete;
          key queue-id;
          leaf queue-id {
            type uint32;
          }

          // system / security / cmp-queue / queue / rate
          container rate {
            tailf:info "Configure Rate";
            tailf:cli-compact-syntax;
            tailf:cli-sequence-commands;
            tailf:cli-embed-no-on-delete;

            leaf value {
              tailf:cli-drop-node-name;
              tailf:cli-no-value-on-delete;
              type union {
                type enumeration {
                  enum max;
                }
                type uint32 {
                  range "1..100000000";
                }
              }
            }

            leaf cir {
              tailf:cli-no-value-on-delete;
              tailf:cli-no-name-on-delete;
              type union {
                type enumeration {
                  enum max;
                }
                type uint32 {
                  range "0..100000000";
                }
              }
            }
          }

          // system / security / cmp-queue / queue / create
          leaf create {
            mandatory true;
            type empty;
            tailf:cli-hide-in-submode;
            tailf:cli-no-name-on-delete;
          }
        }
      }

      // system / security / management-access-filter
      container management-access-filter {
        tailf:info "Configure management access filters";
        tailf:cli-add-mode;

        // system / security / management-access-filter / ip-filter
        container ip-filter {
          tailf:info "Configure a management access IP-filter";
          tailf:cli-add-mode;

          // system / security / management-access-filter / ip-filter /
          // default-action
          leaf default-action {
            tailf:info "Default-action for the management-access-filter";
            tailf:cli-embed-no-on-delete;
            type filter-action;
          }

          // system / security / management-access-filter / ip-filter /
          // entry *
          list entry {
            tailf:info "Match criteria entry for the management-access-filter";
            tailf:cli-embed-no-on-delete;
            key entry-name;
            leaf entry-name {
              type string;
            }

             // system / security / management-access-filter / ip-filter /
            // entry * / action
            leaf action {
              tailf:info "Action to take when a packet matches this entry";
              tailf:cli-no-value-on-delete;
              type filter-action;
            }

            // system / security / management-access-filter / ip-filter /
            // entry * / description
            leaf description {
              tailf:info "Description for this entry";
              tailf:cli-no-value-on-delete;
              type string;
            }

            // system / security / management-access-filter / ip-filter /
            // entry * / src-ip
            leaf src-ip {
              tailf:info "Source IP address of packets to match";
              tailf:cli-no-value-on-delete;
              type union {
                type tailf:ipv4-address-and-prefix-length;
                type string;
              }
            }

            // system / security / management-access-filter / ip-filter /
            // entry * / dst-port
            leaf dst-port {
              tailf:info "TCP/UDP port number or port range to match";
              tailf:cli-no-value-on-delete;
              type uint16;
            }

            // system / security / management-access-filter / ip-filter /
            // entry * / src-port
            leaf src-port {
              tailf:info "Source physical interface to match";
              tailf:cli-no-value-on-delete;
              type string;
            }

            // system / security / management-access-filter / ip-filter /
            // entry * / router
            leaf router {
              tailf:info "Configure router";
              tailf:cli-no-value-on-delete;
              type leafref {
                path "/alu:router/router-name";
              }
            }
          }

          // system / security / management-access-filter / ip-filter /
          // shutdown
          leaf shutdown {
            tailf:info "Start/shutdown the management-access-filter";
            tailf:cli-boolean-no;
            default true;
            type boolean;
          }
        }

        // system / security / management-access-filter / ipv6-filter
        container ipv6-filter {
          tailf:info "Configure a management access IPv6-filter";
          tailf:cli-add-mode;

          // system / security / management-access-filter / ipv6-filter /
          // default-action
          leaf default-action {
            tailf:info "Default-action for the management-access-filter";
            tailf:cli-embed-no-on-delete;
            tailf:cli-no-value-on-delete;
            type filter-action;
          }

          // system / security / management-access-filter / ipv6-filter /
          // entry *
          list entry {
            tailf:info "Match criteria entry for the management-access-filter";
            tailf:cli-embed-no-on-delete;
            key entry-name;
            leaf entry-name {
              type string;
            }

            // system / security / management-access-filter / ipv6-filter /
            // entry * / action
            leaf action {
              tailf:info " Action to take when a packet matches this entry";
              tailf:cli-no-value-on-delete;
              type filter-action;
            }

            // system / security / management-access-filter / ipv6-filter /
            // entry * / description
            leaf description {
              tailf:info "Description for this entry";
              tailf:cli-no-value-on-delete;
              type string;
            }

            // system / security / management-access-filter / ipv6-filter /
            // entry * / src-ip
            leaf src-ip {
              tailf:info "Source IP address of packets to match";
              tailf:cli-no-value-on-delete;
              type union {
                type tailf:ipv6-address-and-prefix-length;
                type string;
              }
            }

            // system / security / management-access-filter / ipv6-filter /
            // entry * / dst-port
            leaf dst-port {
              tailf:info "TCP/UDP port number or port range to match";
              tailf:cli-no-value-on-delete;
              type uint16;
            }

            // system / security / management-access-filter / ipv6-filter /
            // entry * / src-port
            leaf src-port {
              tailf:info "Source physical interface to match";
              tailf:cli-no-value-on-delete;
              type string;
            }
          }

          // system / security / management-access-filter / ipv6-filter /
          // shutdown
          leaf shutdown {
            tailf:info "Start/shutdown the management-access-filter";
            tailf:cli-boolean-no;
            default true;
            type boolean;
          }
        }
      }

      // system / security / vprn-network-exceptions
      leaf vprn-network-exceptions {
        tailf:info "Configure rate for MPLS Exception messages";
        type empty;
      }
    }

    // system / sync-if-timing
    container sync-if-timing {
      tailf:info "Configure synchronous interface timing";
      tailf:cli-add-mode;

      // system / sync-if-timing begin
      container begin {
        tailf:info "Switch to edit mode for sync interface timing";
        tailf:cli-add-mode;
        tailf:cli-explicit-exit;
        tailf:cli-exit-command "commit";

        leaf description {
          type string;
        }
      }
    }
  }

  /// ========================================================================
  /// redundancy /
  /// ========================================================================
  container redundancy {
    tailf:info "Configure redundancy";
    tailf:cli-add-mode;

    // redundancy / multi-chassis
    container multi-chassis {
      tailf:info "Configure multi-chassis parameters";
      tailf:cli-add-mode;

      // redundancy / multi-chassis / peer *
      list peer {
        tailf:info "Configure a multi-chassis redundancy peer";
        tailf:cli-embed-no-on-delete;
        key address;
         leaf address {
          type inet:ipv4-address;
        }

        // redundancy / multi-chassis / peer * / mc-lag
        container mc-lag {
          tailf:info "Configure a Multi-Chassis LAG";
          tailf:cli-embed-no-on-delete;
          tailf:cli-add-mode;

          // redundancy / multi-chassis / peer * / mc-lag / shutdown
          leaf shutdown {
            tailf:info "Administratively enable/disable the MC-LAG";
            tailf:cli-boolean-no;
            default true;
            type boolean;
          }
        }

        // redundancy / multi-chassis / peer * / shutdown
        leaf shutdown {
          tailf:info "Administratively enable/disable the multi-chassis peer";
          tailf:cli-boolean-no;
          default true;
          type boolean;
        }
      }
    }

    // redundancy / synchronize
    leaf synchronize {
      tailf:info "Configure redundancy synchronization parameters";
      tailf:cli-no-value-on-delete;
      type enumeration {
        enum "boot-env";
        enum "config";
      }
    }
  }

  /// ========================================================================
  /// filter /
  /// ========================================================================
  container filter {
    tailf:info "Configuration of filters";
    tailf:cli-add-mode;

    // filter / ip-filter *
    list ip-filter {
      tailf:info "Configure an IP-filter";
      tailf:cli-embed-no-on-delete;
      key ip-filter-name;
      leaf ip-filter-name {
        type string;
      }

      // filter / ip-filter * / create
      leaf create {
        mandatory true;
        type empty;
        tailf:cli-hide-in-submode;
        tailf:cli-no-name-on-delete;
      }

      // filter / ip-filter * / embed-filter *
      list embed-filter {
        tailf:info "Configure embedded filter";
        tailf:cli-embed-no-on-delete;
        tailf:cli-compact-syntax;
        tailf:cli-suppress-mode;
        tailf:cli-sequence-commands;
        key embed-filter-name;

        leaf embed-filter-name {
          tailf:non-strict-leafref {
            path "/alu:filter/ip-filter/ip-filter-name";
          }
          type string;
        }

        // filter / ip-filter * / embed-filter * offset
        leaf offset {
          tailf:cli-no-value-on-delete;
          tailf:cli-no-name-on-delete;
          type uint32;
        }

        // filter / ip-filter * / embed-filter * status
        leaf status {
          tailf:cli-drop-node-name;
          tailf:cli-no-value-on-delete;
          type enumeration {
            enum active;
            enum inactive;
          }
        }
      }

      // filter / ip-filter * / default-action
      leaf default-action {
        tailf:info "Configure default-action for the filter";
        tailf:cli-no-value-on-delete;
        type enumeration {
          enum "drop";
          enum "forward";
        }
      }

      // filter / ip-filter * / scope
      leaf scope {
        tailf:info "Configure scope for this filter";
        tailf:cli-no-value-on-delete;
        type enumeration {
          enum "template";
          enum "exclusive";
          enum "embedded";
        }
      }

      // filter / ip-filter * / description
      leaf description {
        tailf:info "Description for this ip-filter";
        tailf:cli-no-value-on-delete;
        type string;
      }

      // filter / ip-filter * / entry *
      list entry {
        tailf:info "Configure ip-filter entry";
        tailf:cli-embed-no-on-delete;
        uses ip-filter-entry-grouping;
        key entry-name;
        ordered-by user;

        // filter / ip-filter * / entry * / action
        container action {
          tailf:info "Configure action for the filter entry";
          tailf:cli-compact-syntax;
          tailf:cli-sequence-commands;
          tailf:cli-embed-no-on-delete;
          choice action-choice {
            case aa {
              leaf drop {
                tailf:cli-no-name-on-delete;
                type empty;
              }
            }
            case ab {
              leaf nat {
                tailf:cli-no-name-on-delete;
                type empty;
              }
            }
            case ac {
              leaf http-redirect {
                tailf:cli-no-name-on-delete;
                tailf:cli-no-value-on-delete;
                type string;
              }
            }
            case ad {
              container forward {
                tailf:cli-no-name-on-delete;
                presence true;
                container next-hop {
                  tailf:cli-no-name-on-delete;
                  choice next-hop-choice {
                    case na {
                      leaf ip-address {
                        tailf:cli-drop-node-name;
                        tailf:cli-no-value-on-delete;
                        type inet:ipv4-address;
                      }
                    }
                    case nb {
                      leaf indirect {
                        tailf:cli-no-name-on-delete;
                        tailf:cli-no-value-on-delete;
                        type inet:ipv4-address;
                      }
                    }
                    case nc {
                      leaf interface {
                        tailf:cli-no-name-on-delete;
                        tailf:cli-no-value-on-delete;
                        // FIXME depends on ports/lags
                        type string;
                      }
                    }
                  }
                }

                leaf sap {
                  tailf:cli-no-name-on-delete;
                  tailf:cli-no-value-on-delete;
                  type string;
                }

                leaf sdp {
                  tailf:cli-no-name-on-delete;
                  tailf:cli-no-value-on-delete;
                  type string;
                }

                leaf redirect-policy {
                  tailf:cli-no-name-on-delete;
                  tailf:cli-no-value-on-delete;
                  type string;
                }
              }
            }
          }
        }
      }
    }


    // filter / ipv6-filter *
    list ipv6-filter {
      tailf:info "Configure an IPv6-filter";
      tailf:cli-embed-no-on-delete;
      key ip-filter-name;
      leaf ip-filter-name {
        type string;
      }

      // filter / ipv6-filter * / create
      leaf create {
        mandatory true;
        type empty;
        tailf:cli-hide-in-submode;
        tailf:cli-no-name-on-delete;
      }

      // filter / ipv6-filter * / default-action
      leaf default-action {
        tailf:info "Configure default-action for the IPv6-filter";
        tailf:cli-no-value-on-delete;
        type enumeration {
          enum "forward";
          enum "drop";
        }
      }

      // filter / ipv6-filter * / embed-filter *
      list embed-filter {
        tailf:info "Configure embed filter for the IPv6-filter";
        tailf:cli-embed-no-on-delete;
        tailf:cli-compact-syntax;
        tailf:cli-suppress-mode;
        tailf:cli-sequence-commands;
        key embed-filter-name;

        leaf embed-filter-name {
          tailf:non-strict-leafref {
            path "/alu:filter/ipv6-filter/ip-filter-name";
          }
          type string;
        }

        // filter / ipv6-filter * / embed-filter * offset
        leaf offset {
          tailf:cli-embed-no-on-delete;
          tailf:cli-no-value-on-delete;
          tailf:cli-no-name-on-delete;
          type uint32;
        }

        // filter / ipv6-filter * / embed-filter * status
        leaf status {
          tailf:cli-drop-node-name;
          tailf:cli-embed-no-on-delete;
          tailf:cli-no-value-on-delete;
          type enumeration {
            enum active;
            enum inactive;
          }
        }
      }

      // filter / ipv6-filter * / scope
      leaf scope {
        type enumeration {
          enum "embedded";
          enum "exclusive";
          enum "template";
        }
      }

      // filter / ipv6-filter * / description
      leaf description {
        tailf:info "Description for the IPv6-filter";
        tailf:cli-no-value-on-delete;
        type string;
      }

      // filter / ipv6-filter * / entry *
      list entry {
         tailf:info "Configure an IPv6-filter entry";
        tailf:cli-embed-no-on-delete;
        uses ipv6-filter-entry-grouping;
        key entry-name;

        // filter / ipv6-filter * / entry * / action
        leaf action {
          tailf:info " Configure action for the IPv6-filter entry";
          type enumeration {
            enum "drop";
            enum "forward";
          }
        }
      }
    }


    // filter / mac-filter *
    list mac-filter {
      tailf:info "Configure a mac-filter";
      tailf:cli-recursive-delete;
      tailf:cli-embed-no-on-delete;
      key mac-filter-name;
      leaf mac-filter-name {
        type string;
      }

      // filter / mac-filter * / create
      leaf create {
        mandatory true;
        type empty;
        tailf:cli-hide-in-submode;
        tailf:cli-no-name-on-delete;
      }

      // filter / mac-filter * / default-action
      leaf default-action {
        tailf:info "Configure default-action for the filter";
        type enumeration {
          enum "drop";
          enum "forward";
        }
      }

      // filter / mac-filter * / scope
      leaf scope {
        tailf:info "Configure scope for this filter";
        tailf:cli-no-value-on-delete;
        type enumeration {
          enum "exclusive";
          enum "template";
        }
      }

      // filter / mac-filter * / string
      leaf description {
        tailf:info "Description for this mac-filter";
        tailf:cli-no-value-on-delete;
        type string;
      }

      // filter / mac-filter * / entry *
      list entry {
        tailf:info "Configure mac-filter entry";
        tailf:cli-recursive-delete;
        tailf:cli-embed-no-on-delete;
        key entry-name;
        leaf entry-name {
          type string;
        }

        // filter / mac-filter * / entry * / create
        leaf create {
          mandatory true;
          type empty;
          tailf:cli-hide-in-submode;
          tailf:cli-no-name-on-delete;
        }

        // filter / mac-filter * / entry * / description
        leaf description {
          tailf:info "Description for this filter entry";
          tailf:cli-no-value-on-delete;
          type string;
        }

        // filter / mac-filter * / entry * / match /
        container match {
          tailf:info "Configure match criteria for this mac filter entry";
          tailf:cli-add-mode;

          // filter / mac-filter * / entry * / match / dst-mac
          container dst-mac {
            tailf:info "Configure dest. mac match condition";
            tailf:cli-embed-no-on-delete;

            // filter / mac-filter * / entry * / match / dst-mac mac
            leaf mac {
              tailf:cli-drop-node-name;
              tailf:cli-no-value-on-delete;
              type string;
            }

            // filter / mac-filter * / entry * / match / dst-mac mask
            leaf mask {
              tailf:cli-drop-node-name;
              tailf:cli-no-value-on-delete;
              type string;
            }
          }

          // filter / mac-filter * / entry * / match / src-mac
          container src-mac {
            tailf:info "Configure source mac match condition";
            tailf:cli-embed-no-on-delete;

            // filter / mac-filter * / entry * / match / src-mac mac
            leaf mac {
              tailf:cli-drop-node-name;
              tailf:cli-no-value-on-delete;
              type string;
            }

            // filter / mac-filter * / entry * / match / src-mac mask
            leaf mask {
              tailf:cli-drop-node-name;
              tailf:cli-no-value-on-delete;
              type string;
            }
          }

          // filter / mac-filter * / entry * / match / frame-type
          leaf frame-type {
            tailf:cli-hide-in-submode;
            tailf:cli-no-value-on-delete;
            tailf:cli-no-name-on-delete;
            type enumeration {
              enum 802dot3;
              enum 802dot2-llc;
              enum 802dot2-snap;
              enum ethernet_II;
            }
          }

          // filter / mac-filter * / entry * / match / frame-type
          leaf etype {
            tailf:info "Configure e-type match condition";
            tailf:cli-no-value-on-delete;
            when "../frame-type";
            type string;
          }
        }

        // filter / mac-filter * / entry * / action
        container action {
          tailf:info "Configure action for the filter entry";
          tailf:cli-compact-syntax;
          choice choice {
            case drop {
              leaf drop {
                type empty;
              }
            }
            case forward {
              leaf forward {
                type empty;
              }
              leaf sap {
                type string;
              }
            }
          }
        }

        // filter / mac-filter * / entry * / log
        leaf log {
          tailf:info "Configure log for the filter entry";
          tailf:cli-no-value-on-delete;
          type uint32;
        }
      }
    }

    // filter / match-list
    container match-list {
      tailf:info "Configure a match-list for use in a filter";
      tailf:cli-add-mode;

      // filter / match-list / ip-prefix-list *
      list ip-prefix-list {
        tailf:info "Configure an ip prefix list";
        tailf:cli-embed-no-on-delete;
        key name;
        leaf name {
          type string;
        }

        // filter / match-list / ip-prefix-list * / create
        leaf create {
          tailf:cli-hide-in-submode;
          tailf:cli-no-name-on-delete;
          mandatory true;
          type empty;
        }

        // filter / match-list / ip-prefix-list * / description
        leaf description {
          tailf:info "Description for this prefix list";
          tailf:cli-no-value-on-delete;
          type string;
        }

        // filter / match-list / ip-prefix-list * / prefix
        list prefix {
          tailf:info "Create/delete a prefix entry in the prefix list";
          tailf:cli-embed-no-on-delete;
          tailf:cli-suppress-mode;
          key pfx;
          leaf pfx {
            type tailf:ipv4-address-and-prefix-length;
          }
        }
      }

      // filter / match-list / ipv6-prefix-list * /
      list ipv6-prefix-list {
        tailf:info "Configure an ipv6 prefix list";
        tailf:cli-embed-no-on-delete;
        key name;
        leaf name {
          type string;
        }

        // filter / match-list / ipv6-prefix-list * / create
        leaf create {
          tailf:cli-hide-in-submode;
          tailf:cli-no-name-on-delete;
          mandatory true;
          type empty;
        }

        // filter / match-list / ipv6-prefix-list * / description
        leaf description {
          tailf:info "Description for this prefix list";
          tailf:cli-no-value-on-delete;
          type string;
        }

        // filter / match-list / ipv6-prefix-list * / prefix
        list prefix {
          tailf:info "Create/delete a prefix entry in the prefix list";
          tailf:cli-embed-no-on-delete;
          tailf:cli-suppress-mode;
          key pfx;
          leaf pfx {
            type tailf:ipv6-address-and-prefix-length;
          }
        }
      }
    }

    // filter / log *
    list log {
      key log-id;

      leaf log-id {
        type uint32;
      }
      leaf description {
        type string;
      }
      container destination {
        choice choice {
          leaf memory {
            type uint32;
          }
          leaf syslog {
            type uint32;
          }
        }
      }
    }
  }


  /// ========================================================================
  /// test-oam /
  /// ========================================================================
  // test-oam /
  container test-oam {
    tailf:info "Configure Operations, Administration, and Maintenance "+
      "test parameters";
    tailf:cli-add-mode;
    // test-oam / twamp /
    container twamp {
      tailf:info "Configure the Two Way Active Measurement Protocol (TWAMP)";
      tailf:cli-add-mode;
      // test-oam / twamp / server /
      container server {
        tailf:info "Configure the TWAMP server";
        tailf:cli-add-mode;
        tailf:cli-recursive-delete;
        // test-oam / twamp / server / inactivity-timeout
        leaf inactivity-timeout {
          tailf:info "Configure the inactivity timeout for the TWAMP server";
          tailf:cli-no-value-on-delete;
          type uint16 {
            range "60..3600";
          }
          default "900";
        }
        // test-oam / twamp / server / max-conn-server
        leaf max-conn-server {
          tailf:info "Configure the maximum number of control connections "+
            "supported by the TWAMP server";
          tailf:cli-no-value-on-delete;
          type uint8 {
            range "0..64";
          }
          default "32";
        }
        // test-oam / twamp / server / max-sess-server
        leaf max-sess-server {
          tailf:info "Configure the maximum number of sessions supported by "+
            "the TWAMP server";
          tailf:cli-no-value-on-delete;
          type uint8 {
            range "0..64";
          }
          default "32";
        }
        // test-oam / twamp / server / prefix * /
        list prefix {
          key ip-prefix;
          leaf ip-prefix {
            tailf:cli-drop-node-name;
            type tailf:ip-address-and-prefix-length;
          }
          // test-oam / twamp / server / prefix * create
          leaf create {
            mandatory true;
            type empty;
            tailf:cli-hide-in-submode;
            tailf:cli-no-name-on-delete;
          }
          // test-oam / twamp / server / prefix * / description
          leaf description {
            tailf:info "Configure a description for the prefix";
            tailf:cli-no-value-on-delete;
            type string {
              length "1..80";
            }
          }
          // test-oam / twamp / server / prefix * / max-conn-prefix
          leaf max-conn-prefix {
            tailf:info "Configure the maximum number of TWAMP control "+
              "connections supported for the prefix";
            tailf:cli-no-value-on-delete;
            type uint8 {
              range "0..64";
            }
            default "32";
          }
          // test-oam / twamp / server / prefix * / max-sess-prefix
          leaf max-sess-prefix {
            tailf:info "Configure the maximum number of TWAMP sessions "+
              "supported for the prefix";
            tailf:cli-no-value-on-delete;
            type uint8 {
              range "0..64";
            }
            default "32";
          }
        }
        // test-oam / twamp / server / shutdown
        leaf shutdown {
          tailf:cli-boolean-no;
          default true;
          type boolean;
        }
      }
    }
  }



  /// ========================================================================
  /// mirror /
  /// ========================================================================
  container mirror {
    tailf:info "Configure mirror destinations";
    tailf:cli-add-mode;

    // mirror / mirror-dest *
    list mirror-dest {
      tailf:info "Configure a mirror destination";
      tailf:cli-recursive-delete;
      tailf:cli-embed-no-on-delete;
      key service-id;
      leaf service-id {
        type union {
          type uint32 {
            range  "1..2147483690";
          }
          type string {
            length "1..64";
          }
        }
      }

      // mirror / mirror-dest * mirror-type
      leaf mirror-type {
        tailf:cli-hide-in-submode;
        type enumeration {
          enum ether;
          enum frame-relay;
          enum ppp;
          enum ip-only;
          enum atm-sdu;
          enum satop-e1;
          enum satop-t1;
          enum cesopsn;
          enum cesopsn-cas;
        }
      }

      // mirror / mirror-dest * type
      leaf type {
        tailf:cli-no-name-on-delete;
        tailf:cli-no-value-on-delete;
        tailf:cli-hide-in-submode;
        type enumeration {
          enum ether;
          enum frame-relay;
          enum ppp;
          enum ip-only;
          enum atm-sdu;
          enum satop-e1;
          enum satop-t1;
          enum cesopsn;
          enum cesopsn-cas;
        }
      }

      // mirror / mirror-dest * / description
      leaf description {
        tailf:info "Description for this mirror destination";
        tailf:cli-embed-no-on-delete;
        tailf:cli-no-value-on-delete;
        type string;
      }

      // mirror / mirror-dest * enable-port-id
      leaf enable-port-id {
        tailf:info "Include port-id of the system in the packet";
        tailf:cli-embed-no-on-delete;
        type empty;
      }

      // mirror / mirror-dest * encap
      container encap {
        tailf:info "Encapsulation header";
        tailf:cli-add-mode;

        // mirror / mirror-dest * encap / layer-3-encap *
        list layer-3-encap {
          tailf:info "Layer-3 header encapsulation";
          tailf:cli-embed-no-on-delete;
          key encap;
          max-elements 2;

          leaf encap {
            type enumeration {
              enum ip-udp-shim;
              enum ip-gre;
            }
          }

          leaf create {
            tailf:cli-hide-in-submode;
            tailf:cli-no-name-on-delete;
            mandatory true;
            type empty;
          }
        }
      }

      // mirror / mirror-dest * / endpoint
      list endpoint {
        tailf:info "Configure a service end-point";
        tailf:cli-embed-no-on-delete;
        key endpoint-name;

        leaf endpoint-name {
          type string {
            length "1..32";
          }
        }

        // mirror / mirror-dest * / endpoint * / description
        leaf description {
          tailf:info "Description for the service end-point";
          tailf:cli-embed-no-on-delete;
          tailf:cli-no-value-on-delete;
          type string;
        }

        // mirror / mirror-dest * / endpoint * / revert-time
        leaf revert-time {
          tailf:info "Configure the time to wait before reverting to primary"
            + "  spoke-sdp";
          tailf:cli-embed-no-on-delete;
          tailf:cli-no-value-on-delete;
          type union {
            type uint16 {
              range "0..600";
            }
            type enumeration {
              enum infinite;
            }
          }
        }

        // mirror / mirror-dest * / endpoint * / create
        leaf create {
          tailf:cli-hide-in-submode;
          tailf:cli-no-name-on-delete;
          mandatory true;
          type empty;
        }
      }

      // mirror / mirror-dest * / fc
      leaf fc {
        tailf:info "Configure forwarding class for destination traffic";
        tailf:cli-embed-no-on-delete;
        tailf:cli-no-value-on-delete;
        type enumeration {
          enum be;
          enum l2;
          enum af;
          enum l1;
          enum h2;
          enum ef;
          enum h1;
          enum nc;
        }
      }

      // mirror / mirror-dest * / isa-aa-group
      container isa-aa-group {
        tailf:info "Specify ISA Application Assurance Group";
        tailf:cli-embed-no-on-delete;

        // mirror / mirror-dest * / isa-aa-group aa-group-id
        leaf aa-group-id {
          tailf:cli-drop-node-name;
          tailf:cli-no-value-on-delete;
          type uint8 {
            range "1..255";
          }
        }

        // mirror / mirror-dest * / isa-aa-group traffic-direction
        leaf traffic-direction {
          tailf:cli-drop-node-name;
          tailf:cli-no-value-on-delete;
          type enumeration {
            enum from-subscriber;
            enum to-subscriber;
          }
        }
      }

      // mirror / mirror-dest * / remote-source /
      container remote-source  {
        tailf:info "Enable/disable remote-source";
        tailf:cli-add-mode;

        // mirror / mirror-dest * / remote-source / far-end
        leaf far-end {
          tailf:info "Configure Mirror far-end";
          tailf:cli-embed-no-on-delete;
          tailf:cli-no-value-on-delete;
          type inet:ipv4-address;
        }

        // mirror / mirror-dest * / remote-source / spoke-sdp *
        list spoke-sdp {
          tailf:info "Specify SDP <sdp-id>:<vc-id>";
          tailf:cli-embed-no-on-delete;
          tailf:cli-key-format "$(1):$(2)";
          key "sdp-id vc-id";

          leaf sdp-id {
            type uint32;
            tailf:non-strict-leafref {
              path "/alu:service/sdp/sdp-id";
            }
          }

          leaf vc-id {
            type uint32;
          }

          // mirror / mirror-dest * / remote-source / spoke-sdp * endpoint
          leaf endpoint {
            tailf:cli-hide-in-submode;
            tailf:cli-no-name-on-delete;
            tailf:cli-no-value-on-delete;
            type string {
              length "1..32";
            }
          }

          // mirror / mirror-dest * / remote-source / spoke-sdp * / shutdown
          leaf shutdown {
            tailf:cli-boolean-no;
            default true;
            type boolean;
          }
        }
      }

      // mirror / mirror-dest * / sap *
      list sap {
        tailf:info "Specify SAP";
        tailf:cli-embed-no-on-delete;
        key sap-id;
        leaf sap-id {
          type string;
        }

        // mirror / mirror-dest * / sap * / cem /
        container cem {
          tailf:info "Configure CEM properties";
          tailf:cli-add-mode;

          // mirror / mirror-dest * / sap * / cem / packet
          container packet {
            tailf:cli-embed-no-on-delete;

            // mirror / mirror-dest * / sap * / cem / packet jitter-buffer
            leaf jitter-buffer {
              tailf:cli-no-name-on-delete;
              tailf:cli-no-value-on-delete;
              type uint8 {
                range "1..250";
              }
            }

            // mirror / mirror-dest * / sap * / cem / bytes
            leaf bytes {
              tailf:cli-no-name-on-delete;
              tailf:cli-no-value-on-delete;
              type uint16 {
                range "16..2048";
              }
            }
          }

          // mirror / mirror-dest * / sap * / rtp-header
          leaf rtp-header {
            tailf:cli-no-name-on-delete;
            type empty;
          }
        }

        // mirror / mirror-dest * / sap * / egress /
        container egress {
          tailf:info "Configure SAP egress policies";
          tailf:cli-add-mode;

          // mirror / mirror-dest * / sap * / egress / ip-mirror /
          container ip-mirror {
            tailf:info "Configure IP Mirror information";
            tailf:cli-add-mode;

            // mirror / mirror-dest * / sap * / egress / ip-mirror /
            // sa-mac
            leaf sa-mac {
              tailf:cli-embed-no-on-delete;
              type ieee-mac;
            }
          }

          // mirror / mirror-dest * / sap * / egress / ip-mirror / qos
          leaf qos {
            tailf:cli-embed-no-on-delete;
            type uint16;
            tailf:non-strict-leafref {
              path "/alu:qos/sap-egress/policy-id";
            }
          }
        }
      }

      // mirror / mirror-dest * / service-name
      leaf service-name {
        tailf:info "Configure a service-name";
        tailf:cli-embed-no-on-delete;
        tailf:cli-no-value-on-delete;
        type string {
          length "1..64";
        }
      }

      // mirror / mirror-dest * / shutdown
      leaf shutdown {
        tailf:info "Administratively enable/disable the mirror service";
        tailf:cli-boolean-no;
        default true;
        type boolean;
      }

      // mirror / mirror-dest * / slice-size
      leaf slice-size {
        tailf:info "Configure slice-size";
        tailf:cli-embed-no-on-delete;
        tailf:cli-no-value-on-delete;
        type uint16 {
          range "128..9216";
        }
      }

      // mirror / mirror-dest * / spoke-sdp *
      list spoke-sdp {
        tailf:info "Specify SDP <sdp-id>:<vc-id>";
        tailf:cli-key-format "$(1):$(2)";
        key "sdp-id vc-id";

        leaf sdp-id {
          type uint32;
          tailf:non-strict-leafref {
            path "/alu:service/sdp/sdp-id";
          }
        }

        leaf vc-id {
          type uint32;
        }
        // mirror / mirror-dest * / spoke-sdp * / create
        leaf create {
          tailf:cli-hide-in-submode;
          tailf:cli-no-name-on-delete;
          mandatory true;
          type empty;
        }

        // mirror / mirror-dest * / spoke-sdp * endpoint
        leaf endpoint {
          tailf:cli-hide-in-submode;
          tailf:cli-no-name-on-delete;
          tailf:cli-no-value-on-delete;
          type string {
            length "1..32";
          }
        }

        // mirror / mirror-dest * / spoke-sdp * / control-word
        leaf control-word {
          tailf:cli-embed-no-on-delete;
          type empty;
        }

        // mirror / mirror-dest * / spoke-sdp * / precedence
        leaf precedence {
          tailf:cli-embed-no-on-delete;
          tailf:cli-no-value-on-delete;
          type enumeration {
            enum 1;
            enum 2;
            enum 3;
            enum 4;
            enum primary;
          }
        }

        // mirror / mirror-dest * / spoke-sdp * / egress /
        container egress {
          tailf:info "Spoke SDP egress configuration";
          tailf:cli-add-mode;

          // mirror / mirror-dest * / spoke-sdp * / egress /
          // l2tpv3
          container l2tpv3 {
            tailf:cli-no-name-on-delete;

            // mirror / mirror-dest * / spoke-sdp * / egress /
            // l2tpv3 cookie
            leaf cookie {
              tailf:cli-no-name-on-delete;
              tailf:cli-no-value-on-delete;
              type string;
            }
          }

          // mirror / mirror-dest * / spoke-sdp * / egress /
          // vc-label
          leaf vc-label {
            tailf:cli-embed-no-on-delete;
            tailf:cli-no-value-on-delete;
            type uint32 {
              range "16..1048575";
            }
          }
        }

        // mirror / mirror-dest * / spoke-sdp * / ingress /
        container ingress {
          tailf:info "Spoke SDP ingress configuration";
          tailf:cli-add-mode;

          // mirror / mirror-dest * / spoke-sdp * / ingress /
          // vc-label
          leaf vc-label {
            tailf:cli-embed-no-on-delete;
            tailf:cli-no-value-on-delete;
            type uint32 {
              range "2048..18431";
            }
          }
        }

        // mirror / mirror-dest * / spoke-sdp * / ingress /
        // shutdown
        leaf shutdown {
          tailf:cli-boolean-no;
          default true;
          type boolean;
        }
      }

      // mirror / mirror-dest * / spoke-sdp * / create
      leaf create {
        mandatory true;
        type empty;
        tailf:cli-hide-in-submode;
        tailf:cli-no-name-on-delete;
      }
    }
  }


  /// ========================================================================
  /// saa /
  /// ========================================================================
  container saa {
    tailf:info "Configure Service Assurance Agent Tests";
    tailf:cli-add-mode;
    // saa / test * /
    list test {
      tailf:info "Configure SAA test";
      tailf:cli-recursive-delete;
      key test-name;
      leaf test-name {
        type string {
          length "1..32";
        }
      }

      // saa / test * / accounting-policy
      leaf accounting-policy {
        tailf:info "Configure an accounting-policy";
        tailf:cli-no-value-on-delete;
        type leafref{
          path "/alu:log/accounting-policy/acct-policy-id";
        }
      }

      // saa / test * / continuous
      leaf continuous {
        tailf:cli-no-name-on-delete;
        tailf:info "repeat test indefinitely";
        type empty;
      }
      // saa / test * / description
      leaf description {
        tailf:cli-no-value-on-delete;
        tailf:info "Description for this SAA test";
        type string {
          length "1..80";
        }
      }
      // saa / test * / jitter-event
      container jitter-event {
        tailf:info "Configure jitter event threshold";
        tailf:cli-compact-syntax;
        leaf rising-threshold{
          tailf:cli-no-name-on-delete;
          tailf:cli-no-value-on-delete;
          type uint32 {
            range "0..2147483647";
          }
        }
        leaf falling-threshold{
          tailf:cli-no-name-on-delete;
          tailf:cli-no-value-on-delete;
          type uint32 {
            range "0..2147483647";
          }
        }
      }      // saa / test * / latency-event
      container latency-event {
        tailf:info "Configure latency event threshold";
        tailf:cli-compact-syntax;
        leaf rising-threshold{
          tailf:cli-no-name-on-delete;
          tailf:cli-no-value-on-delete;
          type uint32 {
            range "0..2147483647";
          }
        }
        leaf falling-threshold{
          tailf:cli-no-name-on-delete;
          tailf:cli-no-value-on-delete;
          type uint32 {
            range "0..2147483647";
          }
        }
      }
      // saa / test * / loss-event
      container loss-event {
        tailf:info "Configure loss event threshold";
        tailf:cli-compact-syntax;
        leaf rising-threshold{
          tailf:cli-no-name-on-delete;
          tailf:cli-no-value-on-delete;
          type uint32 {
            range "0..2147483647";
          }
        }
        leaf falling-threshold{
          tailf:cli-no-name-on-delete;
          tailf:cli-no-value-on-delete;
          type uint32 {
            range "0..2147483647";
          }
        }
      }

      // saa / test * / type
      container type {
        tailf:cli-add-mode;
        tailf:info "Configure type of SAA test";
        // saa / test * / type / cpe-ping
        container cpe-ping {
          tailf:cli-compact-syntax;
          tailf:info "Configure CPE ping test";
          // saa / test * / type / cpe-ping service
          leaf service{
            tailf:cli-no-name-on-delete;
            tailf:cli-no-value-on-delete;
            type union {
              type uint32 {
                range "1..2147483647";
              }
              type string {
                length "1..64";
              }
            }
          }
          // saa / test * / type / cpe-ping destination
          leaf destination {
            tailf:cli-no-name-on-delete;
            tailf:cli-no-value-on-delete;
            type inet:ipv4-address;
          }
          // saa / test * / type / cpe-ping source
          leaf source {
            tailf:cli-no-name-on-delete;
            tailf:cli-no-value-on-delete;
            type inet:ipv4-address;
          }
          // saa / test * / type / cpe-ping source-mac
          leaf source-mac {
            tailf:cli-no-name-on-delete;
            tailf:cli-no-value-on-delete;
            type ieee-mac;
          }
          // saa / test * / type / cpe-ping fc
          leaf fc {
            tailf:cli-no-name-on-delete;
            tailf:cli-no-value-on-delete;
            type enumeration {
              enum be;
              enum l2;
              enum af;
              enum l1;
              enum h2;
              enum ef;
              enum h1;
              enum nc;
            }
            default "be";
          }
          // saa / test * / type / cpe-ping profile
          leaf profile {
            tailf:cli-no-name-on-delete;
            tailf:cli-no-value-on-delete;
            type enumeration {
              enum in;
              enum out;
            }
            default out;
          }
          // saa / test * / type / cpe-ping ttl
          leaf ttl {
            tailf:cli-no-name-on-delete;
            tailf:cli-no-value-on-delete;
            type uint8 {
              range "1..255";
            }
          }
          // saa / test * / type / cpe-ping count
          leaf count {
            tailf:cli-no-name-on-delete;
            tailf:cli-no-value-on-delete;
            type uint8 {
              range "1..100";
            }
          }
          // saa / test * / type / cpe-ping send-control
          leaf send-control {
            tailf:cli-no-name-on-delete;
            type empty;
          }
          // saa / test * / type / cpe-ping return-control
          leaf return-control {
            tailf:cli-no-name-on-delete;
            type empty;
          }
          // saa / test * / type / cpe-ping interval
          leaf interval {
            tailf:cli-no-name-on-delete;
            tailf:cli-no-value-on-delete;
            type uint8 {
              range "1..10";
            }
          }
        }
        // saa / test * / type / dns
        container dns {
          tailf:info "Configure DNS name resolution test";
          tailf:cli-compact-syntax;
          // saa / test * / type / dns target-addr
          leaf target-addr {
            tailf:cli-no-name-on-delete;
            tailf:cli-no-value-on-delete;
            type string {
              length "1..255";
            }
          }
          // saa / test * / type / dns name-server
          leaf name-server {
            tailf:cli-no-name-on-delete;
            tailf:cli-no-value-on-delete;
            type union {
              type inet:ipv4-address;
              type inet:ipv6-address;
            }
          }
          // saa / test * / type / dns source
          leaf source {
            tailf:cli-no-name-on-delete;
            tailf:cli-no-value-on-delete;
            type union {
              type inet:ipv4-address;
              type inet:ipv6-address;
            }
          }
          // saa / test * / type / dns count
          leaf count {
            tailf:cli-no-name-on-delete;
            tailf:cli-no-value-on-delete;
            type uint8 {
              range "1..100";
            }
            default 1;
          }
          // saa / test * / type / dns timeout
          leaf timeout {
            tailf:cli-no-name-on-delete;
            tailf:cli-no-value-on-delete;
            type uint8 {
              range "1..120";
            }
            default 5;
          }
          // saa / test * / type / dns interval
          leaf interval {
            tailf:cli-no-name-on-delete;
            tailf:cli-no-value-on-delete;
            type uint8 {
              range "1..10";
            }
            default "1";
          }
          // saa / test * / type / dns record-type
          leaf record-type {
            tailf:cli-no-name-on-delete;
            tailf:cli-no-value-on-delete;
            type enumeration {
              enum ipv4-a-record;
              enum ipv6-aaaa-record;
            }
          }
        }
        // saa / test * / type / eth-cfm-two-way-delay
        container eth-cfm-two-way-delay {
          tailf:info "Configure Ethernet Connectivity Fault Management "+
            "two way delay test";
          tailf:cli-compact-syntax;
          leaf mac-address {
            tailf:cli-no-value-on-delete;
            tailf:cli-drop-node-name;
            type ieee-mac;
          }
          // saa / test * / type / eth-cfm-two-way-delay mep
          leaf mep{
            tailf:cli-no-value-on-delete;
            tailf:cli-no-name-on-delete;
            type uint16 {
              range "1..8191";
            }
          }
          // saa / test * / type / eth-cfm-two-way-delay domain
          leaf domain{
            tailf:cli-no-value-on-delete;
            tailf:cli-no-name-on-delete;
            type uint32 {
              range "1..4294967295";
            }
          }
          // saa / test * / type / eth-cfm-two-way-delay association
          leaf association{
            tailf:cli-no-value-on-delete;
            tailf:cli-no-name-on-delete;
            type uint32 {
              range "1..4294967295";
            }
          }
          // saa / test * / type / eth-cfm-two-way-delay fc
          leaf fc {
            tailf:cli-no-value-on-delete;
            tailf:cli-no-name-on-delete;
            type enumeration {
              enum be;
              enum l2;
              enum af;
              enum l1;
              enum h2;
              enum ef;
              enum h1;
              enum nc;
            }
            default nc;
          }
          // saa / test * / type / eth-cfm-two-way-delay profile
          leaf profile {
            tailf:cli-no-value-on-delete;
            tailf:cli-no-name-on-delete;
            type enumeration {
              enum in;
              enum out;
            }
            default in;
          }
          // saa / test * / type / eth-cfm-two-way-delay count
          leaf count{
            tailf:cli-no-value-on-delete;
            tailf:cli-no-name-on-delete;
            type uint16 {
              range "1..1000";
            }
            default 1;
          }
          // saa / test * / type / eth-cfm-two-way-delay timeout
          leaf timeout{
            tailf:cli-no-value-on-delete;
            tailf:cli-no-name-on-delete;
            type uint8 {
              range "1..10";
            }
            default "5";
          }
          // saa / test * / type / eth-cfm-two-way-delay interval
          leaf interval{
            tailf:cli-no-value-on-delete;
            tailf:cli-no-name-on-delete;
            type uint8 {
              range "1..10";
            }
            default 5;
          }
        }
        // saa / test * / type / lsp-ping
        container lsp-ping {
          tailf:cli-compact-syntax;
          tailf:info "";
          leaf lsp-name {
            tailf:cli-drop-node-name;
            type string {
              length "1..64";
            }
          }
          // saa / test * / type / lsp-ping path
          leaf path {
            tailf:cli-no-name-on-delete;
            tailf:cli-no-value-on-delete;
            type string {
              length "1..32";
            }
          }
          // saa / test * / type / lsp-ping fc
          leaf fc {
            tailf:cli-no-value-on-delete;
            tailf:cli-no-name-on-delete;
            type enumeration {
              enum be;
              enum l2;
              enum af;
              enum l1;
              enum h2;
              enum ef;
              enum h1;
              enum nc;
            }
            default be;
          }
          // saa / test * / type / lsp-ping profile
          leaf profile {
            tailf:cli-no-value-on-delete;
            tailf:cli-no-name-on-delete;
            type enumeration {
              enum in;
              enum out;
            }
            default out;
          }
          // saa / test * / type / lsp-ping interval
          leaf interval {
            tailf:cli-no-name-on-delete;
            tailf:cli-no-value-on-delete;
            type uint8 {
              range "1..10";
            }
            default 1;
          }
          // saa / test * / type / lsp-ping send-count
          leaf send-count {
            tailf:cli-no-name-on-delete;
            tailf:cli-no-value-on-delete;
            type uint8 {
              range "1..100";
            }
            default 1;
          }
          // saa / test * / type / lsp-ping size
          leaf size {
            type uint16 {
              range "1..9198";
            }
            default 1;
          }
          // saa / test * / type / lsp-ping src-ip-addr
          leaf src-ip-address {
            tailf:cli-no-name-on-delete;
            tailf:cli-no-value-on-delete;
            type union {
              type inet:ipv4-address;
              type inet:ipv6-address;
            }
          }
          // saa / test * / type / lsp-ping timeout
          leaf timeout {
            tailf:cli-no-name-on-delete;
            tailf:cli-no-value-on-delete;
            type uint8 {
              range "1..10";
            }
            default 5;
          }
          // saa / test * / type / lsp-ping ttl
          leaf ttl {
            tailf:cli-no-name-on-delete;
            tailf:cli-no-value-on-delete;
            type uint8 {
              range "1..255";
            }
            default 255;
          }
        }
        // saa / test * / type / sdp-ping
        container sdp-ping {
          tailf:cli-compact-syntax;
          tailf:info "Configure SDP ping test";
          leaf orig-sdp-id {
            tailf:cli-drop-node-name;
            type uint16 {
              range "1..17407";
            }
          }
          // saa / test * / type / sdp-ping resp-sdp
          leaf resp-sdp {
            tailf:cli-no-name-on-delete;
            tailf:cli-no-value-on-delete;
            type uint16 {
              range "1..17407";
            }
          }
          // saa / test * / type / sdp-ping fc
          leaf fc {
            tailf:cli-no-value-on-delete;
            tailf:cli-no-name-on-delete;
            type enumeration {
              enum be;
              enum l2;
              enum af;
              enum l1;
              enum h2;
              enum ef;
              enum h1;
              enum nc;
            }
            default be;
          }
          // saa / test * / type / sdp-ping profile
          leaf profile {
            tailf:cli-no-value-on-delete;
            tailf:cli-no-name-on-delete;
            type enumeration {
              enum in;
              enum out;
            }
            default out;
          }
          // saa / test * / type / sdp-ping size
          leaf size {
            type uint16 {
              range "72..9198";
            }
            default 72;
          }
          // saa / test * / type / sdp-ping count
          leaf count {
            tailf:cli-no-name-on-delete;
            tailf:cli-no-value-on-delete;
            type uint8 {
              range "1..100";
            }
            default 1;
          }
          // saa / test * / type / sdp-ping timeout
          leaf timeout {
            tailf:cli-no-name-on-delete;
            tailf:cli-no-value-on-delete;
            type uint8 {
              range "1..10";
            }
            default 5;
          }
          // saa / test * / type / sdp-ping interval
          leaf interval {
            tailf:cli-no-name-on-delete;
            tailf:cli-no-value-on-delete;
            type uint8 {
              range "1..10";
            }
            default 1;
          }
        }
        // saa / test * / type / vprn-ping
        container vprn-ping {
          tailf:cli-compact-syntax;
          tailf:info "Configure VPRN ping test";
          leaf service-id {
            tailf:cli-drop-node-name;
            tailf:cli-no-value-on-delete;
            type uint32 {
              range "1..2147483647";
            }
          }
          // saa / test * / type / vprn-ping source
          leaf source {
            tailf:cli-no-name-on-delete;
            tailf:cli-no-value-on-delete;
            type union {
              type inet:ipv4-address;
              type inet:ipv6-address;
            }
          }
          // saa / test * / type / vprn-ping destination
          leaf destination {
            tailf:cli-no-name-on-delete;
            tailf:cli-no-value-on-delete;
            type union {
              type inet:ipv4-address;
              type inet:ipv6-address;
            }
          }
          // saa / test * / type / vprn-ping fc
          leaf fc {
            tailf:cli-no-name-on-delete;
            tailf:cli-no-value-on-delete;
            type enumeration {
              enum be;
              enum l2;
              enum af;
              enum l1;
              enum h2;
              enum ef;
              enum h1;
              enum nc;
            }
            default "be";
          }
          // saa / test * / type / vprn-ping profile
          leaf profile {
            tailf:cli-no-name-on-delete;
            tailf:cli-no-value-on-delete;
            type enumeration {
              enum in;
              enum out;
            }
            default out;
          }
          // saa / test * / type / vprn-ping size
          leaf size {
            tailf:cli-no-name-on-delete;
            tailf:cli-no-value-on-delete;
            type uint16 {
              range "1..9198";
            }
            default 1;
          }
          // saa / test * / type / vprn-ping ttl
          leaf ttl {
            tailf:cli-no-name-on-delete;
            tailf:cli-no-value-on-delete;
            type uint8 {
              range "1..255";
            }
          }
          // saa / test * / type / vprn-ping count
          leaf count {
            tailf:cli-no-name-on-delete;
            tailf:cli-no-value-on-delete;
            type uint8 {
              range "1..100";
            }
          }
          // saa / test * / type / vprn-ping return-control
          leaf return-control {
            tailf:cli-no-name-on-delete;
            type empty;
          }
          // saa / test * / type / vprn-ping timeout
          leaf timeout {
            tailf:cli-no-name-on-delete;
            tailf:cli-no-value-on-delete;
            type uint8 {
              range "1..100";
            }
          }
          // saa / test * / type / vprn-ping interval
          leaf interval {
            tailf:cli-no-name-on-delete;
            tailf:cli-no-value-on-delete;
            type uint8 {
              range "1..10";
            }
          }
        }
      }

      // saa / test * / trap-gen
      container trap-gen {
        tailf:cli-add-mode;
        tailf:info "Configure trap generation for the SAA test";
        // saa / test * / trap-gen / probe-fail-enable
        leaf probe-fail-enable {
          tailf:info "enable trap generation on ping probe failure";
          type empty;
        }
        // saa / test * / trap-gen / probe-fail-threshold
        leaf probe-fail-threshold {
          tailf:info "Configure threshold for trap generation on ping "+
            "probe failure";
          tailf:cli-no-value-on-delete;
          type uint8 {
            range "0..15";
          }
        }
        // saa / test * / trap-gen / test-completion-enable
        leaf test-completion-enable {
          tailf:info "enable trap generation on test completion";
          type empty;
        }
        // saa / test * / trap-gen / test-fail-enable
        leaf test-fail-enable {
          tailf:info "enable trap generation on test failure";
          type empty;
        }
        // saa / test * / trap-gen / test-fail-threshold
        leaf test-fail-threshold {
          tailf:info "configure threshold for trap generation on test failure";
          tailf:cli-no-value-on-delete;
          type uint8 {
            range "0..15";
          }
        }
      }

      // saa / test * / shutdown
      leaf shutdown {
        tailf:info "Administratively enable/disable the mirror source";
        tailf:cli-boolean-no;
        default true;
        type boolean;
      }
    }
  }

  /// ========================================================================
  /// subscriber-mgmt /
  /// ========================================================================
  container subscriber-mgmt {
    tailf:info "Configure subscriber management";
    tailf:cli-add-mode;

    // subscriber-mgmt / authentication-policy *
    list authentication-policy {
      tailf:info "Configure a subscriber authentication policy";
      tailf:cli-recursive-delete;
      tailf:cli-embed-no-on-delete;
      key name;
      leaf name {
        type string;
      }

      // subscriber-mgmt / authentication-policy * / create
      leaf create {
        mandatory true;
        type empty;
        tailf:cli-hide-in-submode;
        tailf:cli-no-name-on-delete;
      }

      // subscriber-mgmt / authentication-policy * / description
      leaf description {
        tailf:info "Description for authentication policy";
        tailf:cli-no-value-on-delete;
        type string;
      }

      // subscriber-mgmt / authentication-policy * / password
      container password {
        tailf:info "Configure the password used in the RADIUS request";
        tailf:cli-compact-syntax;
        tailf:cli-sequence-commands {
          tailf:cli-reset-siblings;
        }
        // subscriber-mgmt / authentication-policy * / password pw
        leaf pw {
          tailf:cli-drop-node-name;
          tailf:cli-no-value-on-delete;
          type string;
        }

        // subscriber-mgmt / authentication-policy * / password hashing-scheme
        leaf hashing-scheme {
          tailf:cli-drop-node-name;
          tailf:cli-no-value-on-delete;
          type enumeration {
            enum hash;
            enum hash2;
          }
        }
      }
    }

    // subscriber-mgmt / sla-profile *
    list sla-profile {
      tailf:info "Configure an SLA profile";
      tailf:cli-recursive-delete;
      tailf:cli-embed-no-on-delete;
      key sla-profile-name;
      leaf sla-profile-name {
        type string;
      }

      // subscriber-mgmt / sla-profile * / create
      leaf create {
        mandatory true;
        type empty;
        tailf:cli-hide-in-submode;
        tailf:cli-no-name-on-delete;
      }

      // subscriber-mgmt / sla-profile * / description
      leaf description {
        tailf:info "Description for this SLA profile";
        tailf:cli-no-value-on-delete;
        type string;
      }

      // subscriber-mgmt / sla-profile * / ingress /
      container ingress {
        tailf:info "Configure ingress parameters";
        tailf:cli-add-mode;

        // subscriber-mgmt / sla-profile * / ingress / qos /
        list qos {
          tailf:info "Apply an ingress qos policy";
          tailf:cli-embed-no-on-delete;
          key id;
          leaf id {
            type uint32;
          }

          // subscriber-mgmt / sla-profile * / ingress / qos /
          // multipoint-shared
          leaf multipoint-shared {
            tailf:cli-hide-in-submode;
            type empty;
          }
        }

        // subscriber-mgmt / sla-profile * / ingress / ip-filter
        leaf ip-filter {
          tailf:info "Configure an ip-filter";
          tailf:cli-no-value-on-delete;
          tailf:non-strict-leafref {
            path "/alu:filter/ip-filter/ip-filter-name";
          }
          type string;
        }

        // subscriber-mgmt / sla-profile * / ingress / ipv6-filter
        leaf ipv6-filter {
          tailf:info "Configure an ipv6-filter";
          tailf:cli-no-value-on-delete;
          tailf:non-strict-leafref {
            path "/alu:filter/ipv6-filter/ip-filter-name";
          }
          type string;
        }

        // subscriber-mgmt / sla-profile * / ingress / qos-marking-from-sap
        leaf qos-marking-from-sap {
          tailf:info "QoS marking from SAP";
          tailf:cli-boolean-no;
          type boolean;
        }
      }

      // subscriber-mgmt / sla-profile * / egress /
      container egress {
        tailf:info "Configure egress parameters";
        tailf:cli-add-mode;

        // subscriber-mgmt / sla-profile * / egress / qos /
        list qos {
          tailf:info "Apply an egress qos policy";
          tailf:cli-embed-no-on-delete;
          key id;
          leaf id {
            type uint32;
          }

          // subscriber-mgmt / sla-profile * / egress / qos /
          // multipoint-shared
          leaf multipoint-shared {
            tailf:cli-hide-in-submode;
            tailf:cli-no-name-on-delete;
            type empty;
          }
        }

        // subscriber-mgmt / sla-profile * / egress / ip-filter
        leaf ip-filter {
          tailf:info "Configure an ip-filter";
          tailf:cli-no-value-on-delete;
          tailf:non-strict-leafref {
            path "/alu:filter/ip-filter/ip-filter-name";
          }
          type string;
        }

        // subscriber-mgmt / sla-profile * / egress / ipv6-filter
        leaf ipv6-filter {
          tailf:info "Configure an ipv6-filter";
          tailf:cli-no-value-on-delete;
          tailf:non-strict-leafref {
            path "/alu:filter/ipv6-filter/ip-filter-name";
          }
          type string;
        }

        // subscriber-mgmt / sla-profile * / egress / qos-marking-from-sap
        leaf qos-marking-from-sap {
          tailf:info "Define the sap-egress qos-policy from which the egress "
                    + "qos marking rules are taken";
          tailf:cli-boolean-no;
          type boolean;
        }
      }
    }

    // subscriber-mgmt / sub-profile *
    list sub-profile {
      tailf:info "Configure a subscriber profile";
      tailf:cli-recursive-delete;
      tailf:cli-embed-no-on-delete;
      key sub-profile-name;
      leaf sub-profile-name {
        type string;
      }

      // subscriber-mgmt / sub-profile * / create
      leaf create {
        mandatory true;
        type empty;
        tailf:cli-hide-in-submode;
        tailf:cli-no-name-on-delete;
      }

      // subscriber-mgmt / sub-profile * / description
      leaf description {
        tailf:info "Description for this subscriber profile";
        tailf:cli-no-value-on-delete;
        type string;
      }

      // subscriber-mgmt / sub-profile * / accounting-policy
      leaf accounting-policy {
        tailf:info "Configure accounting-policy to be used";
        tailf:cli-no-value-on-delete;
        type uint16;
      }

      // subscriber-mgmt / sub-profile * / collect-stats
      leaf collect-stats {
        tailf:info "Enable/disable statistics collection";
        type empty;
      }
    }
  }

  // =========================================================================
  // debug
  // =========================================================================
  container debug {
    tailf:info "Enable/disable debugging and specify debug options";
    tailf:cli-add-mode;

    // debug / mirror-source *
    list mirror-source {
      tailf:info "Configure a mirror source";
      tailf:cli-embed-no-on-delete;
      key service-id;
      leaf service-id {
        type leafref {
          path "/alu:mirror/mirror-dest/service-id";
        }
      }

      // debug / mirror-source * / ingress-label *
      list ingress-label {
        tailf:info "Configure mirroring of ingress MPLS label to a mirror dest";
        tailf:cli-embed-no-on-delete;
        tailf:cli-compact-syntax;
        tailf:cli-suppress-mode;
        key label;
        max-elements 8;

        leaf label {
          type uint32 {
            range "0..1048575";
          }
        }
      }

      // debug / mirror-source * / ip-filter *
      list ip-filter {
        tailf:info "Configure mirroring for an IP filter to a mirror dest";
        tailf:cli-embed-no-on-delete;
        tailf:cli-compact-syntax;
        tailf:cli-suppress-mode;
        key ip-filter-name;
        leaf ip-filter-name {
          tailf:non-strict-leafref {
            path "/alu:filter/ip-filter/ip-filter-name";
          }
          type string;
        }

        // debug / mirror-source * / ip-filter * entry *
        list entry {
          tailf:cli-suppress-mode;
          key id;
          max-elements 8;

          leaf id {
            type uint16 {
              range "1..65535";
            }
          }
        }
      }

      // debug / mirror-source * / mac-filter *
      list mac-filter {
        tailf:info "Configure mirroring matching a mac filter to a mirror dest";
        tailf:cli-embed-no-on-delete;
        tailf:cli-compact-syntax;
        tailf:cli-suppress-mode;
        key mac-filter-name;

        leaf mac-filter-name {
          tailf:non-strict-leafref {
            path "/alu:filter/mac-filter/mac-filter-name";
          }
          type string;
        }

        // debug / mirror-source * / mac-filter * entry
        list entry {
          tailf:cli-suppress-mode;
          key id;
          max-elements 8;

          leaf id {
            type uint16 {
              range "1..65535";
            }
          }
        }
      }

      // debug / mirror-source * / port *
      list port {
        tailf:info "Associate a port with a mirror source";
        tailf:cli-embed-no-on-delete;
        tailf:cli-compact-syntax;
        tailf:cli-suppress-mode;
        key port-id;

        // debug / mirror-source * / port * lag
        leaf lag {
          type empty;
        }

        // debug / mirror-source * / port * port-id
        leaf port-id {
          type string;
        }

        // debug / mirror-source * / port * ingress
        leaf ingress {
          type empty;
        }

        // debug / mirror-source * / port * egress
        leaf egress {
          type empty;
        }
      }

      // debug / mirror-source * / sap *
      list sap {
        tailf:info "Associate a SAP with a mirror-source";
        tailf:cli-embed-no-on-delete;
        tailf:cli-compact-syntax;
        tailf:cli-suppress-mode;
        key sap-id;

        leaf sap-id {
          type string;
        }

        // debug / mirror-source * / sap * ingress
        leaf ingress {
          type empty;
        }

        // debug / mirror-source * / sap * egress
        leaf egress {
          type empty;
        }
      }

      // debug / mirror-source * / sap * subscriber
      list subscriber {
        tailf:info "Add hosts of a subscriber to mirroring service";
        tailf:cli-embed-no-on-delete;
        tailf:cli-compact-syntax;
        tailf:cli-suppress-mode;
        key sub-ident-string;

        leaf sub-ident-string {
          type string;
        }

        // debug / mirror-source * / sap * subscriber * sap
        leaf sap {
          type string;
        }

        // debug / mirror-source * / sap * subscriber * ip
        leaf ip {
          type inet:ipv4-address;
        }

        // debug / mirror-source * / sap * subscriber * mac
        leaf mac {
          type ieee-mac;
        }

        // debug / mirror-source * / sap * subscriber * sla-profile-name
        leaf sla-profile-name {
          type string;
        }

        // debug / mirror-source * / sap * subscriber * fc
        leaf fc {
          type enumeration {
            enum fc;
            enum be;
            enum l2;
            enum af;
            enum l1;
            enum h2;
            enum ef;
            enum h1;
            enum nc;
          }
        }

        // debug / mirror-source * / sap * subscriber * ingress
        leaf ingress {
          type empty;
        }

        // debug / mirror-source * / sap * subscriber * egress
        leaf egress {
          type empty;
        }
      }

      // debug / mirror-source * / sap * subscriber * shutdown
      leaf shutdown {
        tailf:info " Administratively enable/disable the mirror source";
        tailf:cli-boolean-no;
        default true;
        type boolean;

      }
    }
  }


  /// ========================================================================
  /// commands /
  /// ========================================================================
  container commands {
    tailf:cli-drop-node-name;
    tailf:action native-cmd {
      tailf:info "Execute a native command from the NCS CLI";
      tailf:actionpoint ncsinternal {
        tailf:internal;
      }

      input {
        leaf command-string {
          tailf:cli-drop-node-name;
          type string;
        }
      }

      output {
        leaf result {
          type string;
        }
      }
    }
  }
}
